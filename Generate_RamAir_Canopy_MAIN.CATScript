' Generate_RamAir_Canopy_CATIA_REVIEWED_v13_CROSSPORTS_ADAPTIVE.CATScript
' CATIA V5 macro: reads CSV points + rib stations generated by preprocess_ramair_profile.py
' and creates rib splines + upper/lower canopy loft surfaces + rounded TE caps + optional crossport guide curves/cuts.
' v13: crossport cutting defaults to curve-split-first, hides the upstream uncut rib surface, and only uses an adaptive semi-cell-span-based cutter wall as fallback. This removes non-critical CutterWall update warnings when direct curve splitting already creates the hole.
'
' Required files in BASE_FOLDER:
'   ramair_profile_points_for_CATIA.csv
'   ramair_rib_stations.csv
'   ramair_global_inputs.csv
'
' Units: millimetres, degrees.
' BASE_FOLDER can be left blank. The macro resolves CATIA\Inputs from:
'   1) process environment variable RAMAIR_CATIA_INPUTS,
'   2) BASE_FOLDER if manually set below,
'   3) CATIA\Inputs relative to CATIA's current working directory,
'   4) an InputBox prompt.

' v23: compatible with Python v18. Reads grouped folders, exports to BASE_FOLDER\Exports robustly,
' and supports CATIA-safe sharp_extension TE profiles generated in 2D by Python.
' Includes fallback to root-level legacy filenames if folders are not present.
Option Explicit

Const BASE_FOLDER = ""
Const CATIA_INPUTS_ENV = "RAMAIR_CATIA_INPUTS"
Const PROFILE_FILE = "Canopy\ramair_profile_points_for_CATIA.csv"
Const RIB_STATIONS_FILE = "Canopy\ramair_rib_stations.csv"
Const MIDSECTIONS_FILE = "Canopy\ramair_cell_midsections.csv"
Const CROSSPORTS_FILE = "Canopy\ramair_crossports.csv"
Const PARAMS_FILE = "ramair_global_inputs.csv"

' Generation switches. Rib fills are enabled in this version.
Const CREATE_RIB_FILLS = True
Const CREATE_LOFT_PANELS = True

' TE closure: the profile file has a finite TE thickness because upper TE and lower TE
' are different points. CREATE_TE_CLOSURE_PANELS creates the missing spanwise
' cap surface between upper and lower skins at the trailing edge.
Const CREATE_TE_CLOSURE_PANELS = True

Const EXPORT_IGES = True
Const MIN_SPLINE_POINT_DISTANCE_MM = 0.01  ' overwritten conceptually by Python params only if code is edited; kept as safety default

' Fill surfaces are created with G0/point continuity.
' Tangency continuity can fail for curve-only boundaries in CATIA.
Const RIB_FILL_CONTINUITY = 0
Const RIB_BOUNDARY_JOIN_TOLERANCE_MM = 0.05

Dim fso
Dim gWarnings
Dim gSkippedClosePoints
Dim gTeCenterNorm
Dim gProfileMinZNorm
Dim gEnableTERounding
Dim gTEClosureMode
Dim gTeArcPointCount
Dim gAnhedralArcMode
Dim gAnhedralPivotMode
Dim gAnhedralOrientation
Dim gEnableCrossports
Dim gCrossportApplyTo
Dim gCrossportCutMode
Dim gCrossportSplitOrientation
Dim gCrossportCutStrategy
Dim gCrossportCutterExtrudeMm
Dim gEnableFabricThickness
Dim gFabricThicknessMm
Dim gFabricThicknessMode
Dim gFabricThicknessOffsetSide
Dim gFabricThicknessIncludeRibs
Dim gFabricThicknessIncludeStabilizers
Dim gFabricThicknessIncludeTipBulge
Dim gEnableSuspensionTubeGeometry
Dim gDefaultSuspensionLineDiameterMm
Set fso = CreateObject("Scripting.FileSystemObject")
gWarnings = ""
gSkippedClosePoints = 0
gEnableTERounding = False
gTEClosureMode = "rounded"
gTeArcPointCount = 17
gAnhedralArcMode = "center_to_tip_line"
gAnhedralPivotMode = "profile_min_z"
gAnhedralOrientation = "focus_inward"
gEnableCrossports = False
gCrossportApplyTo = "all_internal"
gCrossportCutMode = "post_split_surfaces"
gCrossportSplitOrientation = -1
gCrossportCutStrategy = "curve_split_first"
gCrossportCutterExtrudeMm = 200.0
gEnableFabricThickness = False
gFabricThicknessMm = 0.0
gFabricThicknessMode = "symmetric_offsets"
gFabricThicknessOffsetSide = "normal"
gFabricThicknessIncludeRibs = True
gFabricThicknessIncludeStabilizers = True
gFabricThicknessIncludeTipBulge = True
gEnableSuspensionTubeGeometry = False
gDefaultSuspensionLineDiameterMm = 1.2


Function ResolveBaseFolder()
    Dim shell, envPath, candidate
    envPath = ""
    On Error Resume Next
    Set shell = CreateObject("WScript.Shell")
    envPath = shell.ExpandEnvironmentStrings("%" & CATIA_INPUTS_ENV & "%")
    If Err.Number <> 0 Then
        Err.Clear
        envPath = ""
    End If
    On Error GoTo 0

    If Len(CStr(envPath)) > 0 And CStr(envPath) <> "%" & CATIA_INPUTS_ENV & "%" Then
        If fso.FolderExists(CStr(envPath)) Then
            ResolveBaseFolder = CStr(envPath)
            Exit Function
        End If
    End If

    If Len(CStr(BASE_FOLDER)) > 0 Then
        If fso.FolderExists(CStr(BASE_FOLDER)) Then
            ResolveBaseFolder = CStr(BASE_FOLDER)
            Exit Function
        End If
    End If

    candidate = fso.GetAbsolutePathName("CATIA\Inputs")
    If fso.FolderExists(candidate) Then
        ResolveBaseFolder = candidate
        Exit Function
    End If

    candidate = InputBox("Enter the full path to the CATIA\Inputs folder.", "Ram-air CATIA macro", candidate)
    If Len(CStr(candidate)) > 0 And fso.FolderExists(CStr(candidate)) Then
        ResolveBaseFolder = CStr(candidate)
    Else
        ResolveBaseFolder = ""
    End If
End Function


Function ResolveInputPath(baseFolder, relFile)
    ' Returns baseFolder\relFile, with a legacy fallback to baseFolder\filename
    ' if relFile now points to a grouped subfolder that does not exist.
    Dim p, legacy
    p = baseFolder & "\" & CStr(relFile)
    If fso.FileExists(p) Then
        ResolveInputPath = p
        Exit Function
    End If
    legacy = baseFolder & "\" & fso.GetFileName(CStr(relFile))
    If fso.FileExists(legacy) Then
        ResolveInputPath = legacy
    Else
        ResolveInputPath = p
    End If
End Function

Sub CATMain()

    Dim baseFolder, profilePath, ribPath, midPath, crossportPath, paramPath
    baseFolder = ResolveBaseFolder()
    If Len(CStr(baseFolder)) = 0 Then
        MsgBox "CATIA\Inputs folder not resolved. Set RAMAIR_CATIA_INPUTS or choose a valid folder.", vbCritical, "Ram-air CATIA macro"
        Exit Sub
    End If

    profilePath = ResolveInputPath(baseFolder, PROFILE_FILE)
    ribPath = ResolveInputPath(baseFolder, RIB_STATIONS_FILE)
    midPath = ResolveInputPath(baseFolder, MIDSECTIONS_FILE)
    crossportPath = ResolveInputPath(baseFolder, CROSSPORTS_FILE)
    paramPath = baseFolder & "\" & PARAMS_FILE

    If Not fso.FileExists(profilePath) Then
        MsgBox "Missing file:" & vbCrLf & profilePath, vbCritical, "Ram-air CATIA macro"
        Exit Sub
    End If
    If Not fso.FileExists(ribPath) Then
        MsgBox "Missing file:" & vbCrLf & ribPath, vbCritical, "Ram-air CATIA macro"
        Exit Sub
    End If
    If Not fso.FileExists(paramPath) Then
        MsgBox "Missing file:" & vbCrLf & paramPath, vbCritical, "Ram-air CATIA macro"
        Exit Sub
    End If

    Dim params
    Set params = ReadParamsCsv(paramPath)

    ' CSV parameters override the constants above when present. This allows the
    ' Python preprocessor to drive CATIA without manually editing this macro.
    Dim useRibFills, useLoftPanels, useTEClosurePanels, exportCanopyIges, exportIges, useMidSections
    useRibFills = ParamBool(params, "create_rib_fills", CREATE_RIB_FILLS)
    useLoftPanels = ParamBool(params, "create_loft_panels", CREATE_LOFT_PANELS)
    useTEClosurePanels = ParamBool(params, "create_te_closure_panels", CREATE_TE_CLOSURE_PANELS)
    exportCanopyIges = ParamBool(params, "export_iges", EXPORT_IGES)
    exportIges = ParamBool(params, "export_full_assembly_iges", False)
    useMidSections = ParamBool(params, "use_midcell_distortion_sections", False)

    Dim arcDeg, exportCanopyIgsPath, exportIgsPath, exportStepPath, forceExportToBase, exportStep
    arcDeg = CsvDbl(GetParam(params, "arc_anhedral_deg", "0"))

    gTEClosureMode = LCase(CStr(GetParam(params, "te_closure_mode", "rounded")))
    If gTEClosureMode <> "rounded" And gTEClosureMode <> "straight_gap" And gTEClosureMode <> "sharp_extension" Then gTEClosureMode = "rounded"
    gEnableTERounding = ParamBool(params, "enable_te_rounding", False)
    If gTEClosureMode <> "rounded" Then gEnableTERounding = False
    gTeArcPointCount = CLng(CsvDbl(GetParam(params, "te_rounding_num_points", "17")))
    If gTeArcPointCount < 3 Then gTeArcPointCount = 3
    If (gTeArcPointCount Mod 2) = 0 Then gTeArcPointCount = gTeArcPointCount + 1

    gAnhedralArcMode = LCase(CStr(GetParam(params, "anhedral_arc_mode", "center_to_tip_line")))
    gAnhedralPivotMode = LCase(CStr(GetParam(params, "anhedral_rotation_pivot_mode", "profile_min_z")))
    gAnhedralOrientation = LCase(CStr(GetParam(params, "anhedral_section_orientation", "focus_inward")))
    gEnableCrossports = ParamBool(params, "enable_crossports", False)
    gCrossportApplyTo = LCase(CStr(GetParam(params, "crossport_apply_to", "all_internal")))
    gCrossportCutMode = LCase(CStr(GetParam(params, "crossport_cut_mode", "post_split_surfaces")))
    ' Legacy inner-boundary mode is deliberately redirected to the safer staged Split workflow.
    If gCrossportCutMode = "fill_inner_boundaries" Then gCrossportCutMode = "post_split_surfaces"
    If gCrossportCutMode <> "post_split_surfaces" Then
        If gCrossportCutMode <> "curves_only" Then gCrossportCutMode = "curves_only"
    End If
    gCrossportSplitOrientation = CLng(CsvDbl(GetParam(params, "crossport_split_orientation", "-1")))
    If gCrossportSplitOrientation <> 1 Then gCrossportSplitOrientation = -1

    gCrossportCutStrategy = LCase(CStr(GetParam(params, "crossport_cut_strategy", "curve_split_first")))
    If gCrossportCutStrategy <> "curve_split" And gCrossportCutStrategy <> "extruded_wall_split" And gCrossportCutStrategy <> "curve_split_first" Then
        gCrossportCutStrategy = "curve_split_first"
    End If
    gCrossportCutterExtrudeMm = CsvDbl(GetParam(params, "crossport_cutter_extrude_mm", "0"))
    If gCrossportCutterExtrudeMm < 0.0 Then gCrossportCutterExtrudeMm = 0.0

    gEnableFabricThickness = ParamBool(params, "enable_fabric_thickness", False)
    gFabricThicknessMm = CsvDbl(GetParam(params, "fabric_thickness_mm", "0"))
    If gFabricThicknessMm < 0.0 Then gFabricThicknessMm = 0.0
    gFabricThicknessMode = LCase(CStr(GetParam(params, "fabric_thickness_mode", "symmetric_offsets")))
    If gFabricThicknessMode <> "single_offset" And gFabricThicknessMode <> "symmetric_offsets" Then gFabricThicknessMode = "none"
    gFabricThicknessOffsetSide = LCase(CStr(GetParam(params, "fabric_thickness_offset_side", "normal")))
    gFabricThicknessIncludeRibs = ParamBool(params, "fabric_thickness_include_ribs", True)
    gFabricThicknessIncludeStabilizers = ParamBool(params, "fabric_thickness_include_stabilizers", True)
    gFabricThicknessIncludeTipBulge = ParamBool(params, "fabric_thickness_include_tip_bulge", True)
    gEnableSuspensionTubeGeometry = ParamBool(params, "enable_suspension_tube_geometry", False)
    gDefaultSuspensionLineDiameterMm = CsvDbl(GetParam(params, "default_suspension_line_diameter_mm", "1.2"))
    If gDefaultSuspensionLineDiameterMm <= 0.0 Then gDefaultSuspensionLineDiameterMm = CsvDbl(GetParam(params, "suspension_line_diameter_mm", "1.2"))
    If gDefaultSuspensionLineDiameterMm <= 0.0 Then gDefaultSuspensionLineDiameterMm = 1.2

    exportStep = ParamBool(params, "export_full_assembly_step", False)
    Dim exportCanopyStep
    exportCanopyStep = ParamBool(params, "export_canopy_step", False)

    forceExportToBase = ParamBool(params, "force_export_to_base_folder", True)
    Dim exportFolder, defaultCanopyIgsName, defaultIgsName, defaultStepName
    exportFolder = ResolveRelativePath(CStr(GetParam(params, "exports_subfolder", "Exports")), baseFolder)
    EnsureFolderExists exportFolder
    defaultCanopyIgsName = "ramair_canopy_geometry.igs"
    defaultIgsName = "ramair_full_assembly.igs"
    defaultStepName = "ramair_full_assembly.stp"
    If forceExportToBase Then
        ' Robust mode: always export into the configured exports folder.
        exportCanopyIgsPath = exportFolder & "\" & ExportFileNameFromParam(params, "export_igs_path", defaultCanopyIgsName)
        exportIgsPath = exportFolder & "\" & ExportFileNameFromParam(params, "export_full_assembly_igs_path", defaultIgsName)
        exportStepPath = exportFolder & "\" & ExportFileNameFromParam(params, "export_step_path", defaultStepName)
        EnsureFolderExists exportFolder
    Else
        exportCanopyIgsPath = ResolveExportPath(CStr(GetParam(params, "export_igs_path", exportFolder & "\" & defaultCanopyIgsName)), baseFolder, exportFolder & "\" & defaultCanopyIgsName)
        exportIgsPath = ResolveExportPath(CStr(GetParam(params, "export_full_assembly_igs_path", exportFolder & "\" & defaultIgsName)), baseFolder, exportFolder & "\" & defaultIgsName)
        exportStepPath = ResolveExportPath(CStr(GetParam(params, "export_step_path", exportFolder & "\" & defaultStepName)), baseFolder, exportFolder & "\" & defaultStepName)
    End If

    Dim profileRows, ribRows, midRows, crossportRows
    profileRows = ReadCsvRows(profilePath)
    ribRows = ReadCsvRows(ribPath)

    If gEnableCrossports Then
        If fso.FileExists(crossportPath) Then
            crossportRows = ReadCsvRows(crossportPath)
        Else
            AppendWarning "enable_crossports=1, but missing file: " & crossportPath & ". Rib fills will be created without crossport guide curves."
            gEnableCrossports = False
        End If
    End If

    If useMidSections Then
        If fso.FileExists(midPath) Then
            midRows = ReadCsvRows(midPath)
        Else
            AppendWarning "use_midcell_distortion_sections=1, but missing file: " & midPath & ". The macro will fall back to two-section loft panels."
            useMidSections = False
        End If
    End If

    If Not ValidateInputs(profileRows, ribRows) Then Exit Sub
    If gEnableCrossports Then
        If Not ValidateCrossports(crossportRows) Then
            AppendWarning "Crossport CSV exists but does not contain the expected loop_id/x_chord_norm/z_chord_norm columns. Rib fills will be created without crossport guide curves."
            gEnableCrossports = False
        Else
            If gCrossportCutMode = "curves_only" Then
                AppendWarning "Crossports are enabled in curves_only mode: CATIA will create crossport guide curves after the rib Fill surfaces, but it will not cut holes automatically."
            ElseIf gCrossportCutMode = "post_split_surfaces" Then
                AppendWarning "Crossports are enabled in post_split_surfaces mode: CATIA will create rib Fill surfaces first, then split each internal crossport. Direct curve split is tried first; an adaptive cutter wall is used only as fallback. Upstream uncut surfaces are hidden after each successful cut."
            Else
                AppendWarning "Crossports are enabled in curves_only fallback mode."
            End If
        End If
    End If

    gTeCenterNorm = GetProfileTECenterNorm(profileRows)
    gProfileMinZNorm = GetProfileMinZNorm(profileRows)

    Dim halfSpan
    halfSpan = GetHalfSpanFromRows(ribRows)

    ' v13 safety: if an older Python file did not write crossport_cutter_extrude_mm,
    ' estimate it from the smallest distance between adjacent rib stations.
    ' This is only used by the optional cutter-wall fallback. Direct curve split is tried first.
    If gCrossportCutterExtrudeMm <= 0.0 Then
        gCrossportCutterExtrudeMm = EstimateAdaptiveCutterHalfLength(ribRows)
    End If

    Dim catApp
    Set catApp = CATIA

    Dim partDoc, part, hsf
    Set partDoc = catApp.Documents.Add("Part")
    Set part = partDoc.Part
    Set hsf = part.HybridShapeFactory

    ' PartNumber is not always directly available on PartDocument.
    On Error Resume Next
    partDoc.Product.PartNumber = "RamAir_Canopy_Parametric"
    If Err.Number <> 0 Then
        Err.Clear
        part.Name = "RamAir_Canopy_Parametric"
    End If
    On Error GoTo 0

    Dim hbRibs, hbSurfaces
    Set hbRibs = part.HybridBodies.Add()
    hbRibs.Name = "01_Rib_Curves_From_CSV"
    Set hbSurfaces = part.HybridBodies.Add()
    hbSurfaces.Name = "02_Canopy_Surfaces"

    Dim nRibs
    nRibs = UBound(ribRows, 1)

    If useMidSections Then
        If UBound(midRows, 1) <> nRibs - 1 Then
            AppendWarning "ramair_cell_midsections.csv row count does not match rib station count. Expected " & CStr(nRibs - 1) & " rows, got " & CStr(UBound(midRows, 1)) & ". The macro will fall back to two-section loft panels."
            useMidSections = False
        End If
    End If

    Dim upperSplines(), lowerSplines(), openingLines(), trailingLines(), ribCrossports(), ribFills()
    ReDim upperSplines(nRibs)
    ReDim lowerSplines(nRibs)
    ReDim openingLines(nRibs)
    ReDim trailingLines(nRibs)
    ReDim ribCrossports(nRibs)
    ReDim ribFills(nRibs)

    Dim upperMidSplines(), lowerMidSplines(), trailingMidLines()
    If useMidSections Then
        ReDim upperMidSplines(nRibs - 1)
        ReDim lowerMidSplines(nRibs - 1)
        ReDim trailingMidLines(nRibs - 1)
    End If

    Dim i
    For i = 1 To nRibs
        Dim ribId, yFlat, chord, incDeg, vOff, xOff, thicknessScale, teRadius
        ribId = CLng(CsvDbl(GetCsvValue(ribRows, i, "rib_id")))
        yFlat = CsvDbl(GetCsvValue(ribRows, i, "Y_flat_mm"))
        chord = CsvDbl(GetCsvValue(ribRows, i, "chord_mm"))
        incDeg = CsvDbl(GetCsvValue(ribRows, i, "incidence_deg"))
        vOff = CsvDbl(GetCsvValue(ribRows, i, "vertical_offset_mm"))
        xOff = CsvDbl(GetCsvValueDefault(ribRows, i, "chordwise_offset_mm", "0"))
        thicknessScale = CsvDbl(GetCsvValueDefault(ribRows, i, "thickness_scale", "1"))
        teRadius = CsvDbl(GetCsvValueDefault(ribRows, i, "te_rounding_radius_mm", "0"))

        Dim hbThisRib
        Set hbThisRib = hbRibs.HybridBodies.Add()
        hbThisRib.Name = "Rib_" & CStr(ribId)

        Dim upSpline, loSpline, opLine, teLine
        Set upSpline = MakeSplineFromProfile(part, hsf, hbThisRib, profileRows, "UPPER", yFlat, chord, halfSpan, arcDeg, incDeg, vOff, xOff, thicknessScale, teRadius, "Upper_Rib_" & CStr(ribId))
        Set loSpline = MakeSplineFromProfile(part, hsf, hbThisRib, profileRows, "LOWER", yFlat, chord, halfSpan, arcDeg, incDeg, vOff, xOff, thicknessScale, teRadius, "Lower_Rib_" & CStr(ribId))

        ' IMPORTANT about profile ordering generated by preprocess_ramair_profile.py:
        '   UPPER runs from TE to LE. Therefore UPPER FIRST = upper TE, UPPER LAST = upper LE.
        '   LOWER runs from LE to TE. Therefore LOWER FIRST = lower LE, LOWER LAST = lower TE.
        ' The TE closing line connects LOWER LAST back to UPPER FIRST to close the loop.
        ' The LE opening line connects UPPER LAST to LOWER FIRST.
        Set opLine = MakeLineBetweenProfileEnds(part, hsf, hbThisRib, profileRows, "UPPER", "LAST", "LOWER", "FIRST", yFlat, chord, halfSpan, arcDeg, incDeg, vOff, xOff, thicknessScale, teRadius, "LE_Opening_Rib_" & CStr(ribId))
        If gEnableTERounding Then
            Set teLine = MakeTERoundingCurve(part, hsf, hbThisRib, profileRows, yFlat, chord, halfSpan, arcDeg, incDeg, vOff, xOff, thicknessScale, "TE_Rounded_Rib_" & CStr(ribId))
        ElseIf gTEClosureMode = "sharp_extension" Then
            ' The Python preprocessor has already created a nearly closed sharp TE in the 2D point cloud.
            ' No additional TE cap is needed. If the residual TE gap is nonzero, CATIA can still close
            ' the rib fill from the joined upper/opening/lower loop; if it is too small, avoiding a
            ' separate TE line prevents zero-length AddNewLinePtPt failures.
            Set teLine = Nothing
        Else
            Set teLine = MakeLineBetweenProfileEnds(part, hsf, hbThisRib, profileRows, "LOWER", "LAST", "UPPER", "FIRST", yFlat, chord, halfSpan, arcDeg, incDeg, vOff, xOff, thicknessScale, teRadius, "TE_Close_Rib_" & CStr(ribId))
        End If

        ' Crossport curves are intentionally deferred until after rib Fill surfaces
        ' have been created and updated. This avoids crossport geometry influencing
        ' the stability of the outer rib Fill construction.
        Dim ribCrossportCurves
        Set ribCrossportCurves = Nothing

        Set upperSplines(i) = upSpline
        Set lowerSplines(i) = loSpline
        Set openingLines(i) = opLine
        Set trailingLines(i) = teLine
        Set ribCrossports(i) = ribCrossportCurves

    Next

    If gSkippedClosePoints > 0 Then
        AppendWarning CStr(gSkippedClosePoints) & " near-duplicate point occurrences were skipped to avoid invalid CATIA splines. With 19 ribs this usually means one duplicated/near-duplicated point in the input profile was skipped once per rib."
    End If

    If Not SafePartUpdate(part, "after creating rib curves") Then Exit Sub

    ' Optional virtual mid-cell guide sections for ballooning / thickness increase
    ' and TE rounding. These are not physical ribs. They are used only as extra
    ' loft sections between adjacent rib curves.
    If useMidSections Then
        For i = 1 To nRibs - 1
            Dim midId, yMid, chordMid, incMid, vOffMid, xOffMid, thickMid, teRadMid
            midId = CLng(CsvDbl(GetCsvValueDefault(midRows, i, "midsection_id", CStr(i))))
            yMid = CsvDbl(GetCsvValue(midRows, i, "Y_flat_mm"))
            chordMid = CsvDbl(GetCsvValue(midRows, i, "chord_mm"))
            incMid = CsvDbl(GetCsvValueDefault(midRows, i, "incidence_deg", "0"))
            vOffMid = CsvDbl(GetCsvValueDefault(midRows, i, "vertical_offset_mm", "0"))
            xOffMid = CsvDbl(GetCsvValueDefault(midRows, i, "chordwise_offset_mm", "0"))
            thickMid = CsvDbl(GetCsvValueDefault(midRows, i, "thickness_scale", "1"))
            teRadMid = CsvDbl(GetCsvValueDefault(midRows, i, "te_rounding_radius_mm", "0"))

            Dim hbMid, upMidSpline, loMidSpline, teMidLine
            Set hbMid = hbRibs.HybridBodies.Add()
            hbMid.Name = "MidCell_Guide_" & CStr(midId)

            Set upMidSpline = MakeSplineFromProfile(part, hsf, hbMid, profileRows, "UPPER", yMid, chordMid, halfSpan, arcDeg, incMid, vOffMid, xOffMid, thickMid, teRadMid, "Upper_MidCell_" & CStr(midId))
            Set loMidSpline = MakeSplineFromProfile(part, hsf, hbMid, profileRows, "LOWER", yMid, chordMid, halfSpan, arcDeg, incMid, vOffMid, xOffMid, thickMid, teRadMid, "Lower_MidCell_" & CStr(midId))
            If gEnableTERounding Then
                Set teMidLine = MakeTERoundingCurve(part, hsf, hbMid, profileRows, yMid, chordMid, halfSpan, arcDeg, incMid, vOffMid, xOffMid, thickMid, "TE_Rounded_MidCell_" & CStr(midId))
            ElseIf gTEClosureMode = "sharp_extension" Then
                Set teMidLine = Nothing
            Else
                Set teMidLine = MakeLineBetweenProfileEnds(part, hsf, hbMid, profileRows, "LOWER", "LAST", "UPPER", "FIRST", yMid, chordMid, halfSpan, arcDeg, incMid, vOffMid, xOffMid, thickMid, teRadMid, "TE_Close_MidCell_" & CStr(midId))
            End If

            Set upperMidSplines(i) = upMidSpline
            Set lowerMidSplines(i) = loMidSpline
            Set trailingMidLines(i) = teMidLine
        Next

        If Not SafePartUpdate(part, "after creating mid-cell distortion guide sections") Then Exit Sub
    End If

    ' Build the surface of each rib/cross-section after the curves have been validated.
    If useRibFills Then
        For i = 1 To nRibs
            Dim ribFill
            Set ribFill = TryMakeFill(part, hsf, hbSurfaces, upperSplines(i), openingLines(i), lowerSplines(i), trailingLines(i), ribCrossports(i), "Rib_Fill_" & CStr(i))
            Set ribFills(i) = ribFill
        Next

        If Not SafePartUpdate(part, "after creating rib fill surfaces") Then
            MsgBox "The rib curves were created, but CATIA failed while updating the rib Fill surfaces." & vbCrLf & vbCrLf & _
                   "To inspect the model without rib surfaces, set CREATE_RIB_FILLS = False near the top of the script and run it again.", _
                   vbExclamation, "Ram-air CATIA macro"
            Exit Sub
        End If
    End If

    ' Create crossport guide curves and, optionally, cut the already-valid rib surfaces.
    ' This is deliberately done after the rib Fill update to avoid CATIA failing the Fill
    ' just because a closed internal curve exists in the same rib body.
    If gEnableCrossports Then
        Dim hbCrossports
        Set hbCrossports = part.HybridBodies.Add()
        hbCrossports.Name = "03_Crossport_Curves_And_Cuts"

        For i = 1 To nRibs
            If ShouldApplyCrossportsToRib(ribRows, i, halfSpan) Then
                Dim ribIdCP, yCP, chordCP, incCP, vOffCP, xOffCP, thickCP
                ribIdCP = CLng(CsvDbl(GetCsvValue(ribRows, i, "rib_id")))
                yCP = CsvDbl(GetCsvValue(ribRows, i, "Y_flat_mm"))
                chordCP = CsvDbl(GetCsvValue(ribRows, i, "chord_mm"))
                incCP = CsvDbl(GetCsvValue(ribRows, i, "incidence_deg"))
                vOffCP = CsvDbl(GetCsvValue(ribRows, i, "vertical_offset_mm"))
                xOffCP = CsvDbl(GetCsvValueDefault(ribRows, i, "chordwise_offset_mm", "0"))
                thickCP = CsvDbl(GetCsvValueDefault(ribRows, i, "thickness_scale", "1"))

                Dim hbThisCross, cpCurves
                Set hbThisCross = hbCrossports.HybridBodies.Add()
                hbThisCross.Name = "Crossports_Rib_" & CStr(ribIdCP)
                Set cpCurves = MakeCrossportCurves(part, hsf, hbThisCross, crossportRows, yCP, chordCP, halfSpan, arcDeg, incCP, vOffCP, xOffCP, thickCP, "Crossports_Rib_" & CStr(ribIdCP))
                Set ribCrossports(i) = cpCurves

                If gCrossportCutMode = "post_split_surfaces" Then
                    If Not (ribFills(i) Is Nothing) Then
                        Set ribFills(i) = TryApplyCrossportPostSplits(part, hsf, hbSurfaces, ribFills(i), cpCurves, yCP, halfSpan, arcDeg, "Rib_" & CStr(ribIdCP))
                    End If
                End If
            End If
        Next

        If Not SafePartUpdate(part, "after creating crossport curves/cuts") Then
            MsgBox "The main canopy was created, but CATIA failed while updating crossport curves/cuts." & vbCrLf & vbCrLf & _
                   "Set CROSSPORT_CUT_MODE = curves_only in the Python script or reduce crossport size/number and run again.", _
                   vbExclamation, "Ram-air CATIA macro"
            Exit Sub
        End If
    End If

    ' Build canopy panels between adjacent rib stations.
    If useLoftPanels Then
        For i = 1 To nRibs - 1
            Dim loftU, loftL
            If useMidSections Then
                Set loftU = TryMakeLoft3(part, hsf, hbSurfaces, upperSplines(i), upperMidSplines(i), upperSplines(i+1), "Upper_Surface_Panel_" & CStr(i))
                Set loftL = TryMakeLoft3(part, hsf, hbSurfaces, lowerSplines(i), lowerMidSplines(i), lowerSplines(i+1), "Lower_Surface_Panel_" & CStr(i))
            Else
                Set loftU = TryMakeLoft2(part, hsf, hbSurfaces, upperSplines(i), upperSplines(i+1), "Upper_Surface_Panel_" & CStr(i))
                Set loftL = TryMakeLoft2(part, hsf, hbSurfaces, lowerSplines(i), lowerSplines(i+1), "Lower_Surface_Panel_" & CStr(i))
            End If
        Next

        If Not SafePartUpdate(part, "after creating upper/lower loft panels") Then
            MsgBox "The rib curves were created, but CATIA failed while updating the upper/lower loft surfaces." & vbCrLf & vbCrLf & _
                   "To inspect the ribs only, set CREATE_LOFT_PANELS = False near the top of the script and run it again.", _
                   vbExclamation, "Ram-air CATIA macro"
            Exit Sub
        End If
    End If

    ' Build the spanwise trailing-edge cap surface. This is separate from the
    ' per-rib TE closing lines: without these panels the upper and lower lofts
    ' remain open along the TE even though every rib section has a TE line.
    If useTEClosurePanels Then
        For i = 1 To nRibs - 1
            Dim loftTE
            If Not (trailingLines(i) Is Nothing) And Not (trailingLines(i+1) Is Nothing) Then
                If useMidSections And Not (trailingMidLines(i) Is Nothing) Then
                    Set loftTE = TryMakeLoft3(part, hsf, hbSurfaces, trailingLines(i), trailingMidLines(i), trailingLines(i+1), "TE_Closure_Surface_Panel_" & CStr(i))
                Else
                    Set loftTE = TryMakeLoft2(part, hsf, hbSurfaces, trailingLines(i), trailingLines(i+1), "TE_Closure_Surface_Panel_" & CStr(i))
                End If
            End If
        Next

        If Not SafePartUpdate(part, "after creating trailing-edge closure panels") Then
            MsgBox "The upper/lower skins were created, but CATIA failed while updating the TE closure surfaces." & vbCrLf & vbCrLf & _
                   "To inspect the model without TE cap panels, set CREATE_TE_CLOSURE_PANELS = False near the top of the script and run it again.", _
                   vbExclamation, "Ram-air CATIA macro"
            Exit Sub
        End If
    End If

    ' Export the validated canopy before optional stabilizers, suspension,
    ' payload or other assembly entities are added. This makes export_iges a
    ' genuine canopy-only product instead of an alias of the final assembly.
    If exportCanopyIges Then
        On Error Resume Next
        Err.Clear
        partDoc.ExportData exportCanopyIgsPath, "igs"
        If Err.Number <> 0 Then
            AppendWarning "Canopy surfaces were created, but canopy-only IGES export failed. Target path used: " & exportCanopyIgsPath & ". CATIA error: " & Err.Description & "."
            Err.Clear
        End If
        On Error GoTo 0
    End If

    If exportCanopyStep Then
        On Error Resume Next
        Err.Clear
        partDoc.ExportData exportFolder & "\ramair_canopy_geometry.stp", "stp"
        If Err.Number <> 0 Then
            AppendWarning "Canopy-only STEP export failed: " & Err.Description
            Err.Clear
        End If
        On Error GoTo 0
    End If

    ' Optional canopy-side stabilizers generated independently from the suspension-line network.
    ' They are created after the canopy surfaces are valid and before suspension lines,
    ' because external suspension anchors may later be moved to the stabilizer lower edge
    ' by the Python preprocessor.
    If ParamBool(params, "enable_stabilizers", False) Then
        GenerateStandaloneStabilizersFromCsv part, hsf, baseFolder, params
        If Not SafePartUpdate(part, "after creating independent stabilizer panels") Then
            AppendWarning "CATIA failed while updating independent stabilizer panels. The canopy surfaces were already created; disable ENABLE_CANOPY_STABILIZERS in Python to inspect the base canopy."
        End If
    End If

    ' Optional faceted curved replacement/overlay for the two external tip rib surfaces.
    ' The Python preprocessor creates a grid with lateral bulge in the middle of the
    ' external rib. If requested, the original flat Rib_Fill_1 and Rib_Fill_N are hidden.
    If ParamBool(params, "enable_tip_side_bulge", False) Then
        GenerateTipSideBulgeFromCsv part, hsf, baseFolder, params, ribFills, nRibs
        If Not SafePartUpdate(part, "after creating tip-side bulge panels") Then
            AppendWarning "CATIA failed while updating the optional tip-side bulge panels. The main canopy was already created; disable tip_side_bulge in Python to inspect the base canopy."
        End If
    End If

    ' Optional/experimental fabric-thickness offsets. Recommended workflow for CFD/FEM is
    ' to keep the canopy CAD as mid-surfaces and assign thickness in the mesher/FEM solver
    ' using Canopy\ramair_fabric_shell_properties.csv. Offsets are kept only for explicit tests.
    If gEnableFabricThickness And gFabricThicknessMm > 0.0 Then
        ApplyFabricThicknessOffsets part, hsf
        If Not SafePartUpdate(part, "after creating fabric-thickness offset surfaces") Then
            AppendWarning "CATIA failed while updating experimental fabric-thickness offsets. Use the mid-surface export plus Canopy\ramair_fabric_shell_properties.csv for FEM shell thickness, or thicken after export in the mesher."
        End If
    End If

    ' Optional suspension-line network generated by the Python preprocessor.
    ' This is intentionally done after the canopy surfaces are valid, because the
    ' suspension network is a separate visual/validation layer and should not
    ' affect the surface generation.
    If ParamBool(params, "enable_suspension_lines", False) Then
        GenerateSuspensionLinesFromCsv part, hsf, baseFolder, params
        If Not SafePartUpdate(part, "after creating suspension-line network") Then
            MsgBox "The canopy was created, but CATIA failed while updating the suspension-line network." & vbCrLf & vbCrLf & _
                   "Check ramair_suspension_nodes.csv and ramair_suspension_segments.csv, or temporarily set ENABLE_SUSPENSION_LINES = False in Python.", _
                   vbExclamation, "Ram-air CATIA macro"
            Exit Sub
        End If
    End If

    ' Export the complete visible assembly only when explicitly requested.
    If exportIges Then
        On Error Resume Next
        Err.Clear
        partDoc.ExportData exportIgsPath, "igs"
        If Err.Number <> 0 Then
            AppendWarning "Geometry was created, but IGES export failed. Target path used: " & exportIgsPath & ". CATIA error: " & Err.Description & ". You can still export manually with File > Save As > igs (*.igs)."
            Err.Clear
        End If
        On Error GoTo 0
    End If

    If exportStep Then
        On Error Resume Next
        Err.Clear
        partDoc.ExportData exportStepPath, "stp"
        If Err.Number <> 0 Then
            AppendWarning "Geometry was created, but STEP export failed. Target path used: " & exportStepPath & ". CATIA error: " & Err.Description & ". You can still export manually with File > Save As > stp/step."
            Err.Clear
        End If
        On Error GoTo 0
    End If

    If Len(gWarnings) > 0 Then
        MsgBox "Ram-air canopy macro finished with warnings:" & vbCrLf & vbCrLf & gWarnings, vbExclamation, "Ram-air CATIA macro"
    Else
        MsgBox "Ram-air CATIA generation completed." & vbCrLf & _
               "Canopy export: " & exportCanopyIgsPath & vbCrLf & _
               "Full assembly export: " & exportIgsPath, vbInformation, "Ram-air CATIA macro"
    End If

End Sub

Function MakeSplineFromProfile(part, hsf, hb, profileRows, sectionName, yFlat, chord, halfSpan, arcDeg, incDeg, vOff, xOff, thicknessScale, teRadius, objName)

    Dim spline
    Set spline = hsf.AddNewSpline()
    spline.SetSplineType 0
    spline.SetClosing 0

    Dim r
    Dim hasPrev, lastXn, lastZn, distMm, dxMm, dzMm, pCount
    Dim sectionTotal, sectionCounter, teSign
    sectionTotal = CountSection(profileRows, sectionName)
    sectionCounter = 0
    hasPrev = False
    pCount = 0

    For r = 1 To UBound(profileRows, 1)
        If UCase(GetCsvValue(profileRows, r, "section")) = UCase(sectionName) Then
            Dim xn, zn, p, keepPoint
            xn = CsvDbl(GetCsvValue(profileRows, r, "x_chord_norm"))
            zn = CsvDbl(GetCsvValue(profileRows, r, "z_chord_norm"))
            sectionCounter = sectionCounter + 1
            teSign = 0
            If UCase(sectionName) = "UPPER" And sectionCounter = 1 Then teSign = 1
            If UCase(sectionName) = "LOWER" And sectionCounter = sectionTotal Then teSign = -1

            keepPoint = True
            If hasPrev Then
                dxMm = (xn - lastXn) * chord
                dzMm = (zn - lastZn) * chord
                distMm = Sqr(dxMm * dxMm + dzMm * dzMm)
                If distMm < MIN_SPLINE_POINT_DISTANCE_MM Then
                    keepPoint = False
                    gSkippedClosePoints = gSkippedClosePoints + 1
                End If
            End If

            If keepPoint Then
                Set p = MakeTransformedPoint(part, hsf, hb, xn, zn, yFlat, chord, halfSpan, arcDeg, incDeg, vOff, xOff, thicknessScale, teRadius, teSign, objName & "_P" & CStr(r))
                spline.AddPoint part.CreateReferenceFromObject(p)
                lastXn = xn
                lastZn = zn
                hasPrev = True
                pCount = pCount + 1
            End If
        End If
    Next

    If pCount < 2 Then
        AppendWarning "Spline " & objName & " has fewer than two usable points."
    End If

    spline.Name = objName
    hb.AppendHybridShape spline
    Set MakeSplineFromProfile = spline

End Function

Function MakeLineBetweenProfileEnds(part, hsf, hb, profileRows, secA, endA, secB, endB, yFlat, chord, halfSpan, arcDeg, incDeg, vOff, xOff, thicknessScale, teRadius, objName)

    Dim xn1, zn1, xn2, zn2
    GetProfileEnd profileRows, secA, endA, xn1, zn1
    GetProfileEnd profileRows, secB, endB, xn2, zn2

    Dim p1, p2, line
    Set p1 = MakeTransformedPoint(part, hsf, hb, xn1, zn1, yFlat, chord, halfSpan, arcDeg, incDeg, vOff, xOff, thicknessScale, teRadius, ProfileEndTeSign(secA, endA), objName & "_P1")
    Set p2 = MakeTransformedPoint(part, hsf, hb, xn2, zn2, yFlat, chord, halfSpan, arcDeg, incDeg, vOff, xOff, thicknessScale, teRadius, ProfileEndTeSign(secB, endB), objName & "_P2")
    Set line = hsf.AddNewLinePtPt(part.CreateReferenceFromObject(p1), part.CreateReferenceFromObject(p2))
    line.Name = objName
    hb.AppendHybridShape line
    Set MakeLineBetweenProfileEnds = line

End Function

Function MakeTERoundingCurve(part, hsf, hb, profileRows, yFlat, chord, halfSpan, arcDeg, incDeg, vOff, xOff, thicknessScale, objName)
    ' Automatic rounded TE cap.
    ' The cap is a tangent-continuous spline in the local X-Z rib plane. Its
    ' width is defined by the current LOWER LAST to UPPER FIRST gap after chord
    ' and thickness scaling, while its handles follow the neighbouring lower and
    ' upper profile tangents. This avoids forcing a circular tangent that can
    ' introduce a small curvature reversal at the TE.

    Dim xu, zu, xl, zl, xun, zun, xlp, zlp
    Dim xnU, znU, xnU2, znU2, xnL, znL, xnLP, znLP
    Dim haveU1, haveU2, haveL1, haveLP, r
    haveU1 = False
    haveU2 = False
    haveL1 = False
    haveLP = False
    For r = 1 To UBound(profileRows, 1)
        If UCase(GetCsvValue(profileRows, r, "section")) = "UPPER" Then
            If haveU1 = False Then
                xnU = CsvDbl(GetCsvValue(profileRows, r, "x_chord_norm"))
                znU = CsvDbl(GetCsvValue(profileRows, r, "z_chord_norm"))
                haveU1 = True
            ElseIf haveU2 = False Then
                xnU2 = CsvDbl(GetCsvValue(profileRows, r, "x_chord_norm"))
                znU2 = CsvDbl(GetCsvValue(profileRows, r, "z_chord_norm"))
                haveU2 = True
            End If
        ElseIf UCase(GetCsvValue(profileRows, r, "section")) = "LOWER" Then
            If haveL1 = True Then
                xnLP = xnL
                znLP = znL
                haveLP = True
            End If
            xnL = CsvDbl(GetCsvValue(profileRows, r, "x_chord_norm"))
            znL = CsvDbl(GetCsvValue(profileRows, r, "z_chord_norm"))
            haveL1 = True
        End If
    Next

    If haveU1 = False Or haveL1 = False Then
        GetProfileEnd profileRows, "UPPER", "FIRST", xnU, znU
        GetProfileEnd profileRows, "LOWER", "LAST", xnL, znL
    End If
    If haveU2 = False Then
        xnU2 = xnU - 0.01
        znU2 = znU
    End If
    If haveLP = False Then
        xnLP = xnL - 0.01
        znLP = znL
    End If

    If thicknessScale <= 0.0 Then thicknessScale = 1.0

    xu = xnU * chord + xOff
    zu = znU * thicknessScale * chord + vOff
    xl = xnL * chord + xOff
    zl = znL * thicknessScale * chord + vOff
    xun = xnU2 * chord + xOff
    zun = znU2 * thicknessScale * chord + vOff
    xlp = xnLP * chord + xOff
    zlp = znLP * thicknessScale * chord + vOff

    Dim dx, dz, d
    dx = xu - xl
    dz = zu - zl
    d = Sqr(dx * dx + dz * dz)

    If d < 0.000001 Then
        Set MakeTERoundingCurve = MakeLineBetweenProfileEnds(part, hsf, hb, profileRows, "LOWER", "LAST", "UPPER", "FIRST", yFlat, chord, halfSpan, arcDeg, incDeg, vOff, xOff, thicknessScale, 0.0, objName & "_DegeneratedLine")
        Exit Function
    End If

    Dim t0x, t0z, t1x, t1z, n0, n1, adj0, adj1, handle
    t0x = xl - xlp
    t0z = zl - zlp
    n0 = Sqr(t0x * t0x + t0z * t0z)
    If n0 < 0.000001 Then
        t0x = 1.0
        t0z = 0.0
    Else
        t0x = t0x / n0
        t0z = t0z / n0
    End If
    If t0x < 0.05 Then
        t0x = 0.65 * t0x + 0.35
        n0 = Sqr(t0x * t0x + t0z * t0z)
        t0x = t0x / n0
        t0z = t0z / n0
    End If

    t1x = xun - xu
    t1z = zun - zu
    n1 = Sqr(t1x * t1x + t1z * t1z)
    If n1 < 0.000001 Then
        t1x = -1.0
        t1z = 0.0
    Else
        t1x = t1x / n1
        t1z = t1z / n1
    End If
    If t1x > -0.05 Then
        t1x = 0.65 * t1x - 0.35
        n1 = Sqr(t1x * t1x + t1z * t1z)
        t1x = t1x / n1
        t1z = t1z / n1
    End If

    adj0 = Sqr((xl - xlp) * (xl - xlp) + (zl - zlp) * (zl - zlp))
    adj1 = Sqr((xun - xu) * (xun - xu) + (zun - zu) * (zun - zu))
    handle = 0.70 * 0.5 * (adj0 + adj1)
    If handle < 0.55 * d Then handle = 0.55 * d
    If handle < 0.35 * d Then handle = 0.35 * d
    If handle > 1.35 * d Then handle = 1.35 * d

    Dim p1x, p1z, p2x, p2z
    p1x = xl + handle * t0x
    p1z = zl + handle * t0z
    p2x = xu - handle * t1x
    p2z = zu - handle * t1z
    If p1x <= xl Then
        p1x = xl + handle
        p1z = zl
    End If
    If p2x <= xu Then
        p2x = xu + handle
        p2z = zu
    End If

    Dim spline, i, t, omt, denom, xLocal, zLocal, p
    Set spline = hsf.AddNewSpline()
    spline.SetSplineType 0
    spline.SetClosing 0

    denom = CDbl(gTeArcPointCount - 1)
    For i = 0 To gTeArcPointCount - 1
        t = CDbl(i) / denom
        omt = 1.0 - t
        xLocal = omt * omt * omt * xl + 3.0 * omt * omt * t * p1x + 3.0 * omt * t * t * p2x + t * t * t * xu
        zLocal = omt * omt * omt * zl + 3.0 * omt * omt * t * p1z + 3.0 * omt * t * t * p2z + t * t * t * zu
        Set p = MakeTransformedLocalPoint(part, hsf, hb, xLocal, zLocal, yFlat, chord, halfSpan, arcDeg, incDeg, vOff, thicknessScale, objName & "_P" & CStr(i + 1))
        spline.AddPoint part.CreateReferenceFromObject(p)
    Next

    spline.Name = objName
    hb.AppendHybridShape spline
    Set MakeTERoundingCurve = spline
End Function

Sub GetProfileEnd(profileRows, sectionName, endWhich, ByRef xn, ByRef zn)
    Dim r, found
    found = False
    For r = 1 To UBound(profileRows, 1)
        If UCase(GetCsvValue(profileRows, r, "section")) = UCase(sectionName) Then
            If UCase(endWhich) = "FIRST" And found = False Then
                xn = CsvDbl(GetCsvValue(profileRows, r, "x_chord_norm"))
                zn = CsvDbl(GetCsvValue(profileRows, r, "z_chord_norm"))
                found = True
                Exit Sub
            Else
                xn = CsvDbl(GetCsvValue(profileRows, r, "x_chord_norm"))
                zn = CsvDbl(GetCsvValue(profileRows, r, "z_chord_norm"))
                found = True
            End If
        End If
    Next
End Sub

Function MakeTransformedPoint(part, hsf, hb, xn, zn, yFlat, chord, halfSpan, arcDeg, incDeg, vOff, xOff, thicknessScale, teRadius, teSign, objName)
    Dim xLocal, zLocal
    If thicknessScale <= 0.0 Then thicknessScale = 1.0
    xLocal = xn * chord + xOff
    zLocal = zn * thicknessScale * chord + vOff
    Set MakeTransformedPoint = MakeTransformedLocalPoint(part, hsf, hb, xLocal, zLocal, yFlat, chord, halfSpan, arcDeg, incDeg, vOff, thicknessScale, objName)
End Function

Function MakeTransformedLocalPoint(part, hsf, hb, xLocal, zLocal, yFlat, chord, halfSpan, arcDeg, incDeg, vOff, thicknessScale, objName)
    ' Coordinate convention:
    ' X = chordwise, Y = spanwise, Z = vertical/thickness.
    ' Incidence is applied first in the local X-Z rib plane. The anhedral arc is
    ' then applied in Y-Z around a lower-envelope pivot to avoid the final tip rib
    ' protruding outward beyond the intended span station.

    Dim inc, xInc, zInc
    inc = Deg2Rad(incDeg)
    xInc = xLocal * Cos(inc) + zLocal * Sin(inc)
    zInc = -xLocal * Sin(inc) + zLocal * Cos(inc)

    Dim yArc, zArc, theta, beta, radius
    beta = Deg2Rad(arcDeg)

    If Abs(halfSpan) < 0.000001 Or Abs(beta) < 0.000001 Then
        yArc = yFlat
        zArc = 0.0
        theta = 0.0
    Else
        radius = GetArcRadius(halfSpan, beta)
        theta = GetArcThetaFromProjectedY(yFlat, radius)
        yArc = yFlat
        zArc = radius * (Cos(theta) - 1.0)
    End If

    Dim zPivot, zRel, yFinal, zFinal
    zPivot = GetArcPivotZ(chord, vOff, thicknessScale, incDeg)
    zRel = zInc - zPivot

    If LCase(gAnhedralOrientation) = "legacy_outward" Then
        yFinal = yArc - zRel * Sin(theta)
    Else
        ' Correct ram-air/anhedral orientation:
        ' positive local thickness points radially away from the focus below the canopy.
        ' Therefore the lower side of the rib points inward/down toward the common focus.
        yFinal = yArc + zRel * Sin(theta)
    End If
    zFinal = zArc + zPivot + zRel * Cos(theta)

    Dim p
    Set p = hsf.AddNewPointCoord(xInc, yFinal, zFinal)
    p.Name = objName
    hb.AppendHybridShape p
    Set MakeTransformedLocalPoint = p
End Function

Function GetArcRadius(halfSpan, beta)
    ' Geometry in the Y-Z plane with a circular arc centred below the canopy.
    ' For center_to_tip_line, beta is the aircraft-style anhedral angle between
    ' the root-tip line and the horizontal axis:
    '       z_tip / halfSpan = -tan(beta)
    ' This gives theta_tip = 2*beta and R = halfSpan/sin(2*beta).
    ' For tip_tangent, beta is instead the tangent/rib radial rotation at the tip.
    Dim denom
    If LCase(gAnhedralArcMode) = "tip_tangent" Then
        denom = Sin(beta)
    Else
        denom = Sin(2.0 * beta)
    End If

    If Abs(denom) < 0.000001 Then
        GetArcRadius = 0.0
    Else
        GetArcRadius = halfSpan / denom
    End If
End Function

Function GetArcThetaFromProjectedY(yFlat, radius)
    ' Use projected Y directly. This keeps the stations from drifting laterally.
    ' theta is signed: negative on the left side and positive on the right side.
    If Abs(radius) < 0.000001 Then
        GetArcThetaFromProjectedY = 0.0
    Else
        GetArcThetaFromProjectedY = SafeASin(yFlat / radius)
    End If
End Function

Function SafeASin(x)
    If x > 1.0 Then x = 1.0
    If x < -1.0 Then x = -1.0
    If Abs(Abs(x) - 1.0) < 0.0000001 Then
        If x >= 0.0 Then
            SafeASin = 1.5707963267949
        Else
            SafeASin = -1.5707963267949
        End If
    Else
        SafeASin = Atn(x / Sqr(1.0 - x * x))
    End If
End Function

Function GetArcPivotZ(chord, vOff, thicknessScale, incDeg)
    Dim mode, incAbs
    mode = LCase(gAnhedralPivotMode)
    If thicknessScale <= 0.0 Then thicknessScale = 1.0

    If mode = "profile_zero" Then
        GetArcPivotZ = vOff
    ElseIf mode = "te_center" Then
        GetArcPivotZ = gTeCenterNorm * thicknessScale * chord + vOff
    Else
        ' Default: lower envelope. The small incidence correction avoids the TE/lower
        ' region moving outside the span when the section is rotated nose-up.
        incAbs = Abs(Sin(Deg2Rad(incDeg)))
        GetArcPivotZ = gProfileMinZNorm * thicknessScale * chord + vOff - chord * incAbs
    End If
End Function


Function MakeCrossportCurves(part, hsf, hb, crossportRows, yFlat, chord, halfSpan, arcDeg, incDeg, vOff, xOff, thicknessScale, objPrefix)
    Dim dict
    Set dict = CreateObject("Scripting.Dictionary")

    Dim r, loopId, currentLoopId, spline, p, pCount
    currentLoopId = "__none__"
    pCount = 0
    Set spline = Nothing

    For r = 1 To UBound(crossportRows, 1)
        loopId = CStr(GetCsvValueDefault(crossportRows, r, "loop_id", "1"))

        If loopId <> currentLoopId Then
            If Not spline Is Nothing Then
                If pCount >= 3 Then
                    spline.SetClosing 1
                    spline.Name = objPrefix & "_Loop_" & CStr(currentLoopId)
                    hb.AppendHybridShape spline
                    dict.Add CStr(currentLoopId), spline
                Else
                    AppendWarning "Crossport loop " & CStr(currentLoopId) & " has fewer than 3 usable points and was skipped."
                End If
            End If

            Set spline = hsf.AddNewSpline()
            spline.SetSplineType 0
            spline.SetClosing 1
            currentLoopId = loopId
            pCount = 0
        End If

        Dim xn, zn
        xn = CsvDbl(GetCsvValue(crossportRows, r, "x_chord_norm"))
        zn = CsvDbl(GetCsvValue(crossportRows, r, "z_chord_norm"))

        Set p = MakeTransformedPoint(part, hsf, hb, xn, zn, yFlat, chord, halfSpan, arcDeg, incDeg, vOff, xOff, thicknessScale, 0.0, 0, objPrefix & "_Loop_" & CStr(loopId) & "_P" & CStr(pCount + 1))
        spline.AddPoint part.CreateReferenceFromObject(p)
        pCount = pCount + 1
    Next

    If Not spline Is Nothing Then
        If pCount >= 3 Then
            spline.SetClosing 1
            spline.Name = objPrefix & "_Loop_" & CStr(currentLoopId)
            hb.AppendHybridShape spline
            dict.Add CStr(currentLoopId), spline
        Else
            AppendWarning "Crossport loop " & CStr(currentLoopId) & " has fewer than 3 usable points and was skipped."
        End If
    End If

    Set MakeCrossportCurves = dict
End Function

Sub AddCrossportBoundsToFill(part, fill, crossportCurves)
    ' Robust default: do not add crossport loops as inner Fill boundaries.
    ' CATIA V5 often accepts the Fill object but fails on part.Update when inner
    ' spline loops are used without a support surface or with small tolerance issues.
    ' The safe workflow is to create rib Fill surfaces first and keep crossport curves
    ' as guide/cutting curves. Experimental inner-boundary mode remains available.
    On Error Resume Next
    If crossportCurves Is Nothing Then Exit Sub
    If gCrossportCutMode <> "fill_inner_boundaries" Then Exit Sub

    Dim key
    For Each key In crossportCurves.Keys
        Err.Clear
        fill.AddBound part.CreateReferenceFromObject(crossportCurves(key))
        If Err.Number <> 0 Then
            AppendWarning "CATIA could not add crossport loop " & CStr(key) & " as an inner Fill boundary: " & Err.Description
            Err.Clear
        End If
    Next
    On Error GoTo 0
End Sub

Function ShouldApplyCrossportsToRib(ribRows, rowIdx, halfSpan)
    ShouldApplyCrossportsToRib = False

    Dim yVal, isEnd, isLoaded, ribType
    yVal = CsvDbl(GetCsvValue(ribRows, rowIdx, "Y_flat_mm"))
    isEnd = Abs(Abs(yVal) - Abs(halfSpan)) < 0.001
    If isEnd Then Exit Function

    isLoaded = False
    If HasColumn(ribRows, "is_loaded_rib") Then
        isLoaded = (CLng(CsvDbl(GetCsvValueDefault(ribRows, rowIdx, "is_loaded_rib", "0"))) = 1)
    Else
        ribType = UCase(CStr(GetCsvValueDefault(ribRows, rowIdx, "rib_type", "")))
        If InStr(1, ribType, "LOADED", vbTextCompare) > 0 And InStr(1, ribType, "NON", vbTextCompare) = 0 Then isLoaded = True
    End If

    If gCrossportApplyTo = "loaded_internal" Then
        ShouldApplyCrossportsToRib = isLoaded
    ElseIf gCrossportApplyTo = "nonloaded_internal" Then
        ShouldApplyCrossportsToRib = Not isLoaded
    Else
        ShouldApplyCrossportsToRib = True
    End If
End Function

Function ValidateCrossports(crossportRows)
    ValidateCrossports = False
    If UBound(crossportRows, 1) < 1 Then Exit Function
    If Not HasColumn(crossportRows, "loop_id") Then Exit Function
    If Not HasColumn(crossportRows, "x_chord_norm") Then Exit Function
    If Not HasColumn(crossportRows, "z_chord_norm") Then Exit Function
    ValidateCrossports = True
End Function


Function TryMakeLoft2(part, hsf, hb, curve1, curve2, objName)
    On Error Resume Next
    Err.Clear

    Dim loft
    Set loft = hsf.AddNewLoft()
    If Err.Number <> 0 Then
        AppendWarning "Could not create loft object " & objName & ": " & Err.Description
        Err.Clear
        Set TryMakeLoft2 = Nothing
        On Error GoTo 0
        Exit Function
    End If

    loft.Relimitation = 1
    loft.SectionCoupling = 1
    loft.CanonicalDetection = 2
    loft.AddSectionToLoft part.CreateReferenceFromObject(curve1), 1, Nothing
    loft.AddSectionToLoft part.CreateReferenceFromObject(curve2), 1, Nothing

    If Err.Number <> 0 Then
        AppendWarning "Loft failed: " & objName & ". CATIA error: " & Err.Description
        Err.Clear
        Set TryMakeLoft2 = Nothing
    Else
        loft.Name = objName
        hb.AppendHybridShape loft
        Set TryMakeLoft2 = loft
    End If

    On Error GoTo 0
End Function

Function TryMakeLoft3(part, hsf, hb, curve1, curveMid, curve2, objName)
    On Error Resume Next
    Err.Clear

    Dim loft
    Set loft = hsf.AddNewLoft()
    If Err.Number <> 0 Then
        AppendWarning "Could not create three-section loft object " & objName & ": " & Err.Description
        Err.Clear
        Set TryMakeLoft3 = Nothing
        On Error GoTo 0
        Exit Function
    End If

    loft.Relimitation = 1
    loft.SectionCoupling = 1
    loft.CanonicalDetection = 2
    loft.AddSectionToLoft part.CreateReferenceFromObject(curve1), 1, Nothing
    loft.AddSectionToLoft part.CreateReferenceFromObject(curveMid), 1, Nothing
    loft.AddSectionToLoft part.CreateReferenceFromObject(curve2), 1, Nothing

    If Err.Number <> 0 Then
        AppendWarning "Three-section loft failed: " & objName & ". CATIA error: " & Err.Description
        Err.Clear
        Set TryMakeLoft3 = Nothing
    Else
        loft.Name = objName
        hb.AppendHybridShape loft
        Set TryMakeLoft3 = loft
    End If

    On Error GoTo 0
End Function

Function TryMakeFill(part, hsf, hb, upSpline, opLine, loSpline, teLine, crossportCurves, objName)

    ' Robust strategy:
    '   1) create a joined closed boundary from the four outer curves,
    '   2) create a G0 Fill from that outer boundary,
    '   3) if CATIA rejects the join method, fall back to four separate outer Fill boundaries.
    ' Crossports are normally only guide curves; inner Fill boundary use is experimental.
    '
    ' The boundary loop is:
    '   upper TE -> upper LE,
    '   LE opening upper -> lower,
    '   lower LE -> lower TE,
    '   TE closure lower -> upper.

    Dim boundaryJoin, fill
    Set boundaryJoin = TryMakeBoundaryJoin(part, hsf, hb, upSpline, opLine, loSpline, teLine, objName & "_BoundaryJoin")

    If Not boundaryJoin Is Nothing Then
        Set fill = TryMakeFillFromOneBoundary(part, hsf, hb, boundaryJoin, crossportCurves, objName)
        If Not fill Is Nothing Then
            Set TryMakeFill = fill
            Exit Function
        End If
    End If

    Set fill = TryMakeFillFromFourBoundaries(part, hsf, hb, upSpline, opLine, loSpline, teLine, crossportCurves, objName)
    If fill Is Nothing Then
        AppendWarning "Rib Fill could not be created: " & objName & ". The TE/LE boundary curves were still created, so inspect the rib boundary join in CATIA."
    End If

    Set TryMakeFill = fill

End Function

Function TryMakeBoundaryJoin(part, hsf, hb, upSpline, opLine, loSpline, teLine, objName)
    On Error Resume Next
    Err.Clear

    Dim jn
    Set jn = hsf.AddNewJoin(part.CreateReferenceFromObject(upSpline), part.CreateReferenceFromObject(opLine))
    If Err.Number <> 0 Then
        AppendWarning "Could not start rib boundary join " & objName & ": " & Err.Description
        Err.Clear
        Set TryMakeBoundaryJoin = Nothing
        On Error GoTo 0
        Exit Function
    End If

    jn.AddElement part.CreateReferenceFromObject(loSpline)
    If Not (teLine Is Nothing) Then
        jn.AddElement part.CreateReferenceFromObject(teLine)
    End If

    If Err.Number <> 0 Then
        AppendWarning "Could not add all elements to rib boundary join " & objName & ": " & Err.Description
        Err.Clear
        Set TryMakeBoundaryJoin = Nothing
        On Error GoTo 0
        Exit Function
    End If

    ' These methods/properties exist in most CATIA V5 releases, but some
    ' installations expose slightly different automation members. They are
    ' therefore attempted non-blockingly.
    Err.Clear
    jn.SetConnex 1
    Err.Clear
    jn.SetManifold 1
    Err.Clear
    jn.SetSimplify 0
    Err.Clear
    jn.Tolerance = RIB_BOUNDARY_JOIN_TOLERANCE_MM
    Err.Clear

    jn.Name = objName
    hb.AppendHybridShape jn

    Set TryMakeBoundaryJoin = jn
    On Error GoTo 0
End Function

Function TryMakeFillFromOneBoundary(part, hsf, hb, boundaryCurve, crossportCurves, objName)
    On Error Resume Next
    Err.Clear

    Dim fill
    Set fill = hsf.AddNewFill()
    If Err.Number <> 0 Then
        Err.Clear
        Set TryMakeFillFromOneBoundary = Nothing
        On Error GoTo 0
        Exit Function
    End If

    fill.AddBound part.CreateReferenceFromObject(boundaryCurve)
    AddCrossportBoundsToFill part, fill, crossportCurves
    If Err.Number <> 0 Then
        AppendWarning "Fill from joined boundary failed: " & objName & ". CATIA error: " & Err.Description
        Err.Clear
        Set TryMakeFillFromOneBoundary = Nothing
        On Error GoTo 0
        Exit Function
    End If

    ' G0/point continuity. Do not use tangency continuity for curve-only ribs.
    Err.Clear
    fill.Continuity = RIB_FILL_CONTINUITY
    Err.Clear
    fill.Detection = 2
    Err.Clear

    fill.Name = objName
    hb.AppendHybridShape fill
    Set TryMakeFillFromOneBoundary = fill

    On Error GoTo 0
End Function

Function TryMakeFillFromFourBoundaries(part, hsf, hb, upSpline, opLine, loSpline, teLine, crossportCurves, objName)
    On Error Resume Next
    Err.Clear

    Dim fill
    Set fill = hsf.AddNewFill()
    If Err.Number <> 0 Then
        Err.Clear
        Set TryMakeFillFromFourBoundaries = Nothing
        On Error GoTo 0
        Exit Function
    End If

    ' Boundary order follows the closed profile loop.
    fill.AddBound part.CreateReferenceFromObject(upSpline)
    fill.AddBound part.CreateReferenceFromObject(opLine)
    fill.AddBound part.CreateReferenceFromObject(loSpline)
    If Not (teLine Is Nothing) Then
        fill.AddBound part.CreateReferenceFromObject(teLine)
    End If
    AddCrossportBoundsToFill part, fill, crossportCurves

    If Err.Number <> 0 Then
        AppendWarning "Four-boundary Fill failed: " & objName & ". CATIA error: " & Err.Description
        Err.Clear
        Set TryMakeFillFromFourBoundaries = Nothing
        On Error GoTo 0
        Exit Function
    End If

    Err.Clear
    fill.Continuity = RIB_FILL_CONTINUITY
    Err.Clear
    fill.Detection = 2
    Err.Clear

    fill.Name = objName
    hb.AppendHybridShape fill
    Set TryMakeFillFromFourBoundaries = fill

    On Error GoTo 0
End Function



Function EstimateAdaptiveCutterHalfLength(ribRows)
    ' Fallback if Python did not provide crossport_cutter_extrude_mm.
    ' Uses 35% of the smallest semi-cell spacing with safe clamps.
    On Error Resume Next
    Dim n, i, yPrev, yCur, d, minD, val
    n = UBound(ribRows, 1)
    minD = 0.0
    For i = 2 To n
        yPrev = CsvDbl(GetCsvValue(ribRows, i - 1, "Y_flat_mm"))
        yCur = CsvDbl(GetCsvValue(ribRows, i, "Y_flat_mm"))
        d = Abs(yCur - yPrev)
        If d > 0.000001 Then
            If minD <= 0.0 Or d < minD Then minD = d
        End If
    Next
    If minD <= 0.0 Then minD = 100.0
    val = 0.35 * minD
    If val < 20.0 Then val = 20.0
    If val > 600.0 Then val = 600.0
    EstimateAdaptiveCutterHalfLength = val
    On Error GoTo 0
End Function

Function TryApplyCrossportPostSplits(part, hsf, hb, baseSurface, crossportCurves, yFlat, halfSpan, arcDeg, ribName)
    ' Sequentially cut the already-created rib Fill surface using each crossport loop.
    '
    ' v13 strategy:
    '   - split directly with the closed crossport curve first, because this is stable
    '     once the upstream uncut Fill is hidden after every successful cut.
    '   - if direct splitting fails, an adaptive semi-cell-span-based cutter wall is
    '     used as fallback. The fixed 200 mm wall is no longer required.
    On Error Resume Next

    Dim currentSurface
    Set currentSurface = baseSurface

    If currentSurface Is Nothing Then
        Set TryApplyCrossportPostSplits = baseSurface
        On Error GoTo 0
        Exit Function
    End If
    If crossportCurves Is Nothing Then
        Set TryApplyCrossportPostSplits = currentSurface
        On Error GoTo 0
        Exit Function
    End If

    Dim key, splitCandidate, previousSurface
    For Each key In crossportCurves.Keys
        Set previousSurface = currentSurface
        Set splitCandidate = TrySplitSurfaceByCrossport(part, hsf, hb, currentSurface, crossportCurves(key), yFlat, halfSpan, arcDeg, ribName & "_CrossportCut_" & CStr(key), gCrossportSplitOrientation)
        If splitCandidate Is Nothing Then
            AppendWarning "Crossport cut " & CStr(key) & " could not be applied on " & ribName & ". The guide curve was kept; reduce size, move the crossport away from the rib boundary, or try crossport_cut_strategy=extruded_wall_split with the adaptive cutter-wall fallback."
        Else
            HideFeatureSafely previousSurface
            Set currentSurface = splitCandidate
        End If
    Next

    Set TryApplyCrossportPostSplits = currentSurface
    On Error GoTo 0
End Function

Function TrySplitSurfaceByCrossport(part, hsf, hb, surfaceFeature, curveFeature, yFlat, halfSpan, arcDeg, objName, preferredOrientation)
    ' v13 strategy:
    '   1) By default, try direct curve Split first. In the current model this is the
    '      most stable method once the upstream uncut Rib_Fill is hidden.
    '   2) If direct curve Split fails and the strategy allows it, create an adaptive
    '      cutter wall and try wall Split as fallback.
    '   3) Do not report cutter-wall failures as warnings if the direct split already
    '      created the hole. This avoids confusing non-critical messages.
    Dim splitObj, cutterObj, wallFailText
    wallFailText = ""

    If gCrossportCutStrategy = "curve_split_first" Or gCrossportCutStrategy = "curve_split" Then
        Set splitObj = TryOneSurfaceSplit(part, hsf, hb, surfaceFeature, curveFeature, objName & "_Curve_O" & CStr(preferredOrientation), preferredOrientation)
        If splitObj Is Nothing Then
            Set splitObj = TryOneSurfaceSplit(part, hsf, hb, surfaceFeature, curveFeature, objName & "_Curve_O" & CStr(-preferredOrientation), -preferredOrientation)
        End If
        If Not (splitObj Is Nothing) Then
            Set TrySplitSurfaceByCrossport = splitObj
            Exit Function
        End If
        If gCrossportCutStrategy = "curve_split" Then
            Set TrySplitSurfaceByCrossport = Nothing
            Exit Function
        End If
    End If

    ' Wall fallback or forced wall-first mode. The half-length is now written by Python
    ' from semi-cell spacing, so it scales with model size and avoids the previous fixed 200 mm assumption.
    Set cutterObj = TryMakeCrossportCuttingWall(part, hsf, hb, curveFeature, yFlat, halfSpan, arcDeg, objName & "_CutterWall")
    If Not (cutterObj Is Nothing) Then
        Set splitObj = TryOneSurfaceSplit(part, hsf, hb, surfaceFeature, cutterObj, objName & "_Wall_O" & CStr(preferredOrientation), preferredOrientation)
        If splitObj Is Nothing Then
            Set splitObj = TryOneSurfaceSplit(part, hsf, hb, surfaceFeature, cutterObj, objName & "_Wall_O" & CStr(-preferredOrientation), -preferredOrientation)
        End If
        HideFeatureSafely cutterObj
        If Not (splitObj Is Nothing) Then
            Set TrySplitSurfaceByCrossport = splitObj
            Exit Function
        End If
    Else
        wallFailText = " CATIA rejected the adaptive cutter wall; direct curve split had already been attempted."
    End If

    ' If wall-first was forced, use curve fallback after wall failure.
    If gCrossportCutStrategy = "extruded_wall_split" Then
        Set splitObj = TryOneSurfaceSplit(part, hsf, hb, surfaceFeature, curveFeature, objName & "_CurveFallback_O" & CStr(preferredOrientation), preferredOrientation)
        If splitObj Is Nothing Then
            Set splitObj = TryOneSurfaceSplit(part, hsf, hb, surfaceFeature, curveFeature, objName & "_CurveFallback_O" & CStr(-preferredOrientation), -preferredOrientation)
        End If
        If Not (splitObj Is Nothing) Then
            Set TrySplitSurfaceByCrossport = splitObj
            Exit Function
        End If
    End If

    If Len(wallFailText) > 0 Then AppendWarning "Crossport split failed for " & objName & "." & wallFailText
    Set TrySplitSurfaceByCrossport = Nothing
End Function

Function TryMakeCrossportCuttingWall(part, hsf, hb, curveFeature, yFlat, halfSpan, arcDeg, objName)
    On Error Resume Next
    Err.Clear

    Dim dirObj, extObj, L
    Set dirObj = MakeRibNormalDirection(hsf, yFlat, halfSpan, arcDeg)
    If Err.Number <> 0 Or dirObj Is Nothing Then
        AppendWarning "Could not create crossport cutter direction for " & objName & ": " & Err.Description
        Err.Clear
        Set TryMakeCrossportCuttingWall = Nothing
        On Error GoTo 0
        Exit Function
    End If

    L = gCrossportCutterExtrudeMm
    If L < 1.0 Then L = EstimateAdaptiveCutterHalfLengthFromScalars(halfSpan)

    Set extObj = hsf.AddNewExtrude(part.CreateReferenceFromObject(curveFeature), -L, L, dirObj)
    If Err.Number <> 0 Or extObj Is Nothing Then
        AppendWarning "Could not create crossport cutter wall " & objName & ": " & Err.Description
        Err.Clear
        Set TryMakeCrossportCuttingWall = Nothing
        On Error GoTo 0
        Exit Function
    End If

    extObj.Name = objName
    hb.AppendHybridShape extObj
    If Not SafeUpdateObjectOrDeleteSilent(part, extObj, objName) Then
        Set TryMakeCrossportCuttingWall = Nothing
    Else
        Set TryMakeCrossportCuttingWall = extObj
    End If

    On Error GoTo 0
End Function

Function EstimateAdaptiveCutterHalfLengthFromScalars(halfSpan)
    Dim val
    val = 0.35 * Abs(halfSpan) / 10.0
    If val < 20.0 Then val = 20.0
    If val > 600.0 Then val = 600.0
    EstimateAdaptiveCutterHalfLengthFromScalars = val
End Function

Function MakeRibNormalDirection(hsf, yFlat, halfSpan, arcDeg)
    ' Returns a direction approximately normal to the rib section plane.
    ' For focus_inward anhedral, the local rib normal in the Y-Z plane is
    ' proportional to (0, -cos(theta), sin(theta)). Its opposite is equivalent
    ' for creating a through-cut wall; Split orientation controls kept side.
    Dim beta, radius, theta, ny, nz
    beta = Deg2Rad(arcDeg)

    If Abs(halfSpan) < 0.000001 Or Abs(beta) < 0.000001 Then
        theta = 0.0
    Else
        radius = GetArcRadius(halfSpan, beta)
        theta = GetArcThetaFromProjectedY(yFlat, radius)
    End If

    If LCase(gAnhedralOrientation) = "legacy_outward" Then
        ny = -Cos(theta)
        nz = -Sin(theta)
    Else
        ny = -Cos(theta)
        nz = Sin(theta)
    End If

    Set MakeRibNormalDirection = hsf.AddNewDirectionByCoord(0.0, ny, nz)
End Function

Function TryOneSurfaceSplit(part, hsf, hb, surfaceFeature, cutterFeature, objName, orientation)
    On Error Resume Next
    Err.Clear

    Dim splitObj
    Set splitObj = hsf.AddNewHybridSplit(part.CreateReferenceFromObject(surfaceFeature), part.CreateReferenceFromObject(cutterFeature), CLng(orientation))
    If Err.Number <> 0 Or splitObj Is Nothing Then
        Err.Clear
        Set TryOneSurfaceSplit = Nothing
        On Error GoTo 0
        Exit Function
    End If

    splitObj.Name = objName
    hb.AppendHybridShape splitObj

    If Not SafeUpdateObjectOrDelete(part, splitObj, objName) Then
        Set TryOneSurfaceSplit = Nothing
    Else
        Set TryOneSurfaceSplit = splitObj
    End If

    On Error GoTo 0
End Function

Function SafeUpdateObjectOrDeleteSilent(part, featureObj, featureName)
    On Error Resume Next
    Err.Clear
    part.UpdateObject featureObj
    If Err.Number <> 0 Then
        Err.Clear
        part.InWorkObject = featureObj
        On Error Resume Next
        part.HybridShapeFactory.DeleteObjectForDatum part.CreateReferenceFromObject(featureObj)
        Err.Clear
        SafeUpdateObjectOrDeleteSilent = False
    Else
        SafeUpdateObjectOrDeleteSilent = True
    End If
    On Error GoTo 0
End Function

Function SafeUpdateObjectOrDelete(part, featureObj, featureName)
    On Error Resume Next
    Err.Clear

    part.UpdateObject featureObj
    If Err.Number <> 0 Then
        Err.Clear
        part.Update
    End If

    If Err.Number <> 0 Then
        AppendWarning "CATIA rejected feature " & featureName & ": " & Err.Description
        Err.Clear
        DeleteFeatureSafely featureObj
        SafeUpdateObjectOrDelete = False
    Else
        SafeUpdateObjectOrDelete = True
    End If

    On Error GoTo 0
End Function

Sub DeleteFeatureSafely(featureObj)
    On Error Resume Next
    Err.Clear
    Dim sel
    Set sel = CATIA.ActiveDocument.Selection
    sel.Clear
    sel.Add featureObj
    sel.Delete
    sel.Clear
    Err.Clear
    On Error GoTo 0
End Sub

Sub HideFeatureSafely(featureObj)
    ' Move an upstream construction/result surface to No Show after a downstream
    ' split succeeds. This is critical: otherwise the full uncut Rib_Fill remains
    ' visible underneath the split and the crossport looks like only an imprinted circle.
    On Error Resume Next
    Err.Clear
    Dim sel
    Set sel = CATIA.ActiveDocument.Selection
    sel.Clear
    sel.Add featureObj
    sel.VisProperties.SetShow 1
    sel.Clear
    Err.Clear
    On Error GoTo 0
End Sub


Function ResolveRelativePath(pathText, baseFolder)
    Dim s
    s = Trim(CStr(pathText))
    s = Replace(s, "/", "\")
    If Len(s) = 0 Then
        ResolveRelativePath = baseFolder
    ElseIf IsAbsoluteWindowsPath(s) Then
        ResolveRelativePath = s
    Else
        ResolveRelativePath = baseFolder & "\" & s
    End If
End Function

Function ResolveExportPath(rawPath, baseFolder, defaultFileName)
    ' Resolve export paths robustly.  Relative paths keep their subfolders
    ' under BASE_FOLDER; empty paths use the full defaultFileName.

    Dim s, p
    s = Trim(CStr(rawPath))
    If Len(s) = 0 Then s = CStr(defaultFileName)
    s = Replace(s, "/", "\")

    If IsAbsoluteWindowsPath(s) Then
        p = s
    ElseIf InStr(s, "\") > 0 Then
        p = baseFolder & "\" & s
    Else
        p = baseFolder & "\" & s
    End If

    EnsureFolderExists fso.GetParentFolderName(p)
    ResolveExportPath = p
End Function

Function ExportFileNameFromParam(params, key, defaultName)
    Dim raw, nameOnly
    raw = CStr(GetParam(params, key, defaultName))
    raw = Replace(raw, "/", "\")
    nameOnly = fso.GetFileName(raw)
    If Len(nameOnly) = 0 Then nameOnly = CStr(defaultName)
    ExportFileNameFromParam = nameOnly
End Function

Function IsAbsoluteWindowsPath(pathText)
    Dim s
    s = Trim(CStr(pathText))
    IsAbsoluteWindowsPath = False

    If Len(s) >= 3 Then
        If Mid(s, 2, 2) = ":\" Then
            IsAbsoluteWindowsPath = True
            Exit Function
        End If
    End If

    If Len(s) >= 2 Then
        If Left(s, 2) = "\\" Then
            IsAbsoluteWindowsPath = True
            Exit Function
        End If
    End If
End Function

Sub EnsureFolderExists(folderPath)
    Dim parentPath
    folderPath = Trim(CStr(folderPath))
    If Len(folderPath) = 0 Then Exit Sub
    If fso.FolderExists(folderPath) Then Exit Sub

    parentPath = fso.GetParentFolderName(folderPath)
    If Len(parentPath) > 0 And parentPath <> folderPath Then
        EnsureFolderExists parentPath
    End If

    On Error Resume Next
    Err.Clear
    fso.CreateFolder folderPath
    If Err.Number <> 0 Then
        AppendWarning "Could not create export folder: " & folderPath & ". CATIA/FileSystem error: " & Err.Description
        Err.Clear
    End If
    On Error GoTo 0
End Sub

Function ReadParamsCsv(filePath)
    Dim dict
    Set dict = CreateObject("Scripting.Dictionary")

    Dim ts, header, line, parts
    Set ts = fso.OpenTextFile(filePath, 1)
    header = ts.ReadLine

    Do Until ts.AtEndOfStream
        line = Trim(ts.ReadLine)
        If Len(line) > 0 Then
            parts = Split(line, ",")
            If UBound(parts) >= 1 Then dict(Trim(parts(0))) = Trim(parts(1))
        End If
    Loop

    ts.Close
    Set ReadParamsCsv = dict
End Function

Function GetParam(dict, key, defaultValue)
    If dict.Exists(key) Then
        GetParam = dict(key)
    Else
        GetParam = defaultValue
    End If
End Function


Function ParamBool(dict, key, defaultValue)
    If dict.Exists(key) Then
        ParamBool = TextToBool(dict(key), defaultValue)
    Else
        ParamBool = defaultValue
    End If
End Function

Function TextToBool(valueText, defaultValue)
    Dim s
    s = UCase(Trim(CStr(valueText)))
    If s = "1" Or s = "TRUE" Or s = "YES" Or s = "Y" Then
        TextToBool = True
    ElseIf s = "0" Or s = "FALSE" Or s = "NO" Or s = "N" Then
        TextToBool = False
    Else
        TextToBool = defaultValue
    End If
End Function

Function GetCsvValueDefault(arr, rowIdx, colName, defaultValue)
    If HasColumn(arr, colName) Then
        GetCsvValueDefault = GetCsvValue(arr, rowIdx, colName)
    Else
        GetCsvValueDefault = defaultValue
    End If
End Function

Function ProfileEndTeSign(sectionName, endWhich)
    ProfileEndTeSign = 0
    If UCase(sectionName) = "UPPER" And UCase(endWhich) = "FIRST" Then ProfileEndTeSign = 1
    If UCase(sectionName) = "LOWER" And UCase(endWhich) = "LAST" Then ProfileEndTeSign = -1
End Function

Function GetProfileTECenterNorm(profileRows)
    Dim upX, upZ, loX, loZ
    GetProfileEnd profileRows, "UPPER", "FIRST", upX, upZ
    GetProfileEnd profileRows, "LOWER", "LAST", loX, loZ
    GetProfileTECenterNorm = 0.5 * (upZ + loZ)
End Function

Function GetProfileMinZNorm(profileRows)
    Dim r, zVal, minZ, first
    first = True
    minZ = 0.0
    For r = 1 To UBound(profileRows, 1)
        zVal = CsvDbl(GetCsvValue(profileRows, r, "z_chord_norm"))
        If first Then
            minZ = zVal
            first = False
        ElseIf zVal < minZ Then
            minZ = zVal
        End If
    Next
    GetProfileMinZNorm = minZ
End Function

Function ReadCsvRows(filePath)
    Dim ts, headerLine, headers, lines(), lineCount, line, vals, i, j
    Set ts = fso.OpenTextFile(filePath, 1)
    headerLine = ts.ReadLine
    headers = Split(headerLine, ",")

    lineCount = 0
    ReDim lines(0)

    Do Until ts.AtEndOfStream
        line = Trim(ts.ReadLine)
        If Len(line) > 0 Then
            lineCount = lineCount + 1
            ReDim Preserve lines(lineCount)
            lines(lineCount) = line
        End If
    Loop
    ts.Close

    Dim arr()
    ReDim arr(lineCount, UBound(headers) + 1)

    For j = 0 To UBound(headers)
        arr(0, j+1) = Trim(headers(j))
    Next

    For i = 1 To lineCount
        vals = Split(lines(i), ",")
        For j = 0 To UBound(headers)
            If j <= UBound(vals) Then
                arr(i, j+1) = Trim(vals(j))
            Else
                arr(i, j+1) = ""
            End If
        Next
    Next

    ReadCsvRows = arr
End Function

Function GetCsvValue(arr, rowIdx, colName)
    Dim j
    For j = 1 To UBound(arr, 2)
        If UCase(arr(0, j)) = UCase(colName) Then
            GetCsvValue = arr(rowIdx, j)
            Exit Function
        End If
    Next
    GetCsvValue = ""
End Function

Function HasColumn(arr, colName)
    Dim j
    HasColumn = False
    For j = 1 To UBound(arr, 2)
        If UCase(arr(0, j)) = UCase(colName) Then
            HasColumn = True
            Exit Function
        End If
    Next
End Function

Function CountSection(profileRows, sectionName)
    Dim r, c
    c = 0
    For r = 1 To UBound(profileRows, 1)
        If UCase(GetCsvValue(profileRows, r, "section")) = UCase(sectionName) Then c = c + 1
    Next
    CountSection = c
End Function

Function ValidateInputs(profileRows, ribRows)
    ValidateInputs = False

    If UBound(profileRows, 1) < 2 Then
        MsgBox "Profile CSV has no usable point rows.", vbCritical, "Ram-air CATIA macro"
        Exit Function
    End If

    If UBound(ribRows, 1) < 2 Then
        MsgBox "Rib-station CSV has too few rib rows.", vbCritical, "Ram-air CATIA macro"
        Exit Function
    End If

    Dim requiredProfileCols, requiredRibCols, c
    requiredProfileCols = Array("section", "x_chord_norm", "z_chord_norm")
    For Each c In requiredProfileCols
        If Not HasColumn(profileRows, CStr(c)) Then
            MsgBox "Missing column in profile CSV: " & CStr(c), vbCritical, "Ram-air CATIA macro"
            Exit Function
        End If
    Next

    requiredRibCols = Array("rib_id", "Y_flat_mm", "chord_mm", "incidence_deg", "vertical_offset_mm")
    For Each c In requiredRibCols
        If Not HasColumn(ribRows, CStr(c)) Then
            MsgBox "Missing column in rib-station CSV: " & CStr(c), vbCritical, "Ram-air CATIA macro"
            Exit Function
        End If
    Next

    If CountSection(profileRows, "UPPER") < 2 Then
        MsgBox "Profile CSV must contain at least two UPPER points.", vbCritical, "Ram-air CATIA macro"
        Exit Function
    End If

    If CountSection(profileRows, "LOWER") < 2 Then
        MsgBox "Profile CSV must contain at least two LOWER points.", vbCritical, "Ram-air CATIA macro"
        Exit Function
    End If

    ValidateInputs = True
End Function

Function GetHalfSpanFromRows(rows)
    Dim i, yVal, maxAbs
    maxAbs = 0.0

    For i = 1 To UBound(rows, 1)
        yVal = Abs(CsvDbl(GetCsvValue(rows, i, "Y_flat_mm")))
        If yVal > maxAbs Then maxAbs = yVal
    Next

    GetHalfSpanFromRows = maxAbs
End Function

Function CsvDbl(v)
    ' Locale-independent number parser for CATScript/VBScript.
    ' It accepts both decimal points and decimal commas, without using Val
    ' because Val is not available in CATScript's VBScript engine.

    Dim s, mantissa, expText, expPos
    Dim i, ch, digit, code
    Dim sign, expSign
    Dim value, fracDiv, expValue
    Dim inFraction

    s = Trim(CStr(v))
    s = Replace(s, " ", "")

    If Len(s) = 0 Then
        CsvDbl = 0.0
        Exit Function
    End If

    ' Remove possible CSV quotes.
    If Left(s, 1) = Chr(34) And Right(s, 1) = Chr(34) And Len(s) >= 2 Then
        s = Mid(s, 2, Len(s) - 2)
    End If

    ' Split possible scientific notation, e.g. 1.23E-4.
    expPos = InStr(1, s, "E", vbTextCompare)
    If expPos > 0 Then
        mantissa = Left(s, expPos - 1)
        expText = Mid(s, expPos + 1)
    Else
        mantissa = s
        expText = "0"
    End If

    sign = 1
    If Left(mantissa, 1) = "-" Then
        sign = -1
        mantissa = Mid(mantissa, 2)
    ElseIf Left(mantissa, 1) = "+" Then
        mantissa = Mid(mantissa, 2)
    End If

    value = 0.0
    fracDiv = 1.0
    inFraction = False

    For i = 1 To Len(mantissa)
        ch = Mid(mantissa, i, 1)
        code = Asc(ch)

        If code = 46 Or code = 44 Then
            inFraction = True
        ElseIf code >= 48 And code <= 57 Then
            digit = code - 48

            If inFraction Then
                fracDiv = fracDiv * 10.0
                value = value + digit / fracDiv
            Else
                value = value * 10.0 + digit
            End If
        End If
    Next

    expSign = 1
    expValue = 0
    expText = Trim(expText)

    If Len(expText) > 0 Then
        If Left(expText, 1) = "-" Then
            expSign = -1
            expText = Mid(expText, 2)
        ElseIf Left(expText, 1) = "+" Then
            expText = Mid(expText, 2)
        End If

        For i = 1 To Len(expText)
            ch = Mid(expText, i, 1)
            code = Asc(ch)
            If code >= 48 And code <= 57 Then
                digit = code - 48
                expValue = expValue * 10 + digit
            End If
        Next
    End If

    CsvDbl = sign * value * (10.0 ^ (expSign * expValue))
End Function

Function Deg2Rad(deg)
    Deg2Rad = CsvDbl(deg) * 3.14159265358979 / 180.0
End Function


Function SafePartUpdate(part, stageName)
    On Error Resume Next
    Err.Clear
    part.Update

    If Err.Number <> 0 Then
        MsgBox "CATIA part.Update failed " & stageName & "." & vbCrLf & vbCrLf & _
               "CATIA error: " & Err.Description & vbCrLf & vbCrLf & _
               "Most likely causes:" & vbCrLf & _
               "1) an invalid rib Fill surface," & vbCrLf & _
               "2) two profile points too close to each other," & vbCrLf & _
               "3) a loft section that CATIA cannot couple," & vbCrLf & _
               "4) if crossport cuts are enabled, crossport loops too close to the rib outer boundary." & vbCrLf & vbCrLf & _
               "This version creates rib fills first, then applies crossport splits after the Fill surfaces are valid.", _
               vbCritical, "Ram-air CATIA macro"
        Err.Clear
        SafePartUpdate = False
    Else
        SafePartUpdate = True
    End If

    On Error GoTo 0
End Function

Sub AppendWarning(msg)
    If Len(gWarnings) > 0 Then gWarnings = gWarnings & vbCrLf & vbCrLf
    gWarnings = gWarnings & "- " & msg
End Sub


' =============================================================================
' Independent canopy stabilizer generation
' =============================================================================
Sub GenerateStandaloneStabilizersFromCsv(part, hsf, baseFolder, params)
    Dim nodesFile, segFile, surfFile, nodesPath, segPath, surfPath
    nodesFile = CStr(GetParam(params, "stabilizer_nodes_file", "ramair_stabilizer_nodes.csv"))
    segFile = CStr(GetParam(params, "stabilizer_segments_file", "ramair_stabilizer_segments.csv"))
    surfFile = CStr(GetParam(params, "stabilizer_surfaces_file", "ramair_stabilizer_surfaces.csv"))
    nodesPath = ResolveInputPath(baseFolder, nodesFile)
    segPath = ResolveInputPath(baseFolder, segFile)
    surfPath = ResolveInputPath(baseFolder, surfFile)

    If Not fso.FileExists(nodesPath) Then
        AppendWarning "enable_stabilizers=1, but missing file: " & nodesPath
        Exit Sub
    End If

    Dim nodeRows
    nodeRows = ReadCsvRows(nodesPath)
    If UBound(nodeRows, 1) < 1 Then
        AppendWarning "Stabilizers enabled but stabilizer node table is empty."
        Exit Sub
    End If

    Dim hbStab, hbNodes, hbSegs
    Set hbStab = part.HybridBodies.Add()
    hbStab.Name = "03B_Canopy_Stabilizers"
    Set hbNodes = hbStab.HybridBodies.Add()
    hbNodes.Name = "Stabilizer_Nodes"
    Set hbSegs = hbStab.HybridBodies.Add()
    hbSegs.Name = "Stabilizer_Boundaries"

    Dim nodeDict
    Set nodeDict = CreateObject("Scripting.Dictionary")

    Dim i, nid, x, y, z, p
    For i = 1 To UBound(nodeRows, 1)
        nid = SanitizeCatiaName(CStr(GetCsvValue(nodeRows, i, "node_id")))
        x = CsvDbl(GetCsvValue(nodeRows, i, "x_mm"))
        y = CsvDbl(GetCsvValue(nodeRows, i, "y_mm"))
        z = CsvDbl(GetCsvValue(nodeRows, i, "z_mm"))
        Set p = hsf.AddNewPointCoord(x, y, z)
        p.Name = nid
        hbNodes.AppendHybridShape p
        If nodeDict.Exists(nid) Then nodeDict.Remove nid
        nodeDict.Add nid, p
        TrySetFeatureColor p, 180, 110, 40
    Next

    If fso.FileExists(segPath) Then
        Dim segRows, sid, s1, s2, lineObj
        segRows = ReadCsvRows(segPath)
        For i = 1 To UBound(segRows, 1)
            sid = SanitizeCatiaName(CStr(GetCsvValue(segRows, i, "segment_id")))
            s1 = SanitizeCatiaName(CStr(GetCsvValue(segRows, i, "start_node")))
            s2 = SanitizeCatiaName(CStr(GetCsvValue(segRows, i, "end_node")))
            If nodeDict.Exists(s1) And nodeDict.Exists(s2) Then
                Set lineObj = hsf.AddNewLinePtPt(part.CreateReferenceFromObject(nodeDict.Item(s1)), part.CreateReferenceFromObject(nodeDict.Item(s2)))
                lineObj.Name = sid
                hbSegs.AppendHybridShape lineObj
                TrySetFeatureColor lineObj, 180, 110, 40
            Else
                AppendWarning "Stabilizer boundary segment skipped due to missing node: " & sid & " (" & s1 & " -> " & s2 & ")"
            End If
        Next
    End If

    If fso.FileExists(surfPath) Then
        GenerateGenericSurfacesFromCsv part, hsf, hbStab, nodeDict, surfPath, "Stabilizer_Surfaces", "Stabilizer_Surface_Boundaries"
    End If
End Sub


Sub GenerateTipSideBulgeFromCsv(part, hsf, baseFolder, params, ribFills, nRibs)
    Dim nodesFile, segFile, secFile, surfFile, nodesPath, segPath, secPath, surfPath
    nodesFile = CStr(GetParam(params, "tip_bulge_nodes_file", "ramair_tip_bulge_nodes.csv"))
    segFile = CStr(GetParam(params, "tip_bulge_segments_file", "ramair_tip_bulge_segments.csv"))
    secFile = CStr(GetParam(params, "tip_bulge_sections_file", "ramair_tip_bulge_sections.csv"))
    surfFile = CStr(GetParam(params, "tip_bulge_surfaces_file", "ramair_tip_bulge_surfaces.csv"))
    nodesPath = ResolveInputPath(baseFolder, nodesFile)
    segPath = ResolveInputPath(baseFolder, segFile)
    secPath = ResolveInputPath(baseFolder, secFile)
    surfPath = ResolveInputPath(baseFolder, surfFile)

    If Not fso.FileExists(nodesPath) Then
        AppendWarning "enable_tip_side_bulge=1, but missing file: " & nodesPath
        Exit Sub
    End If

    Dim nodeRows
    nodeRows = ReadCsvRows(nodesPath)
    If UBound(nodeRows, 1) < 1 Then
        AppendWarning "Tip-side bulge enabled but node table is empty."
        Exit Sub
    End If

    Dim hbTip, hbNodes, hbSegs
    Set hbTip = part.HybridBodies.Add()
    hbTip.Name = "03C_Tip_Side_Bulge"
    Set hbNodes = hbTip.HybridBodies.Add()
    hbNodes.Name = "Tip_Bulge_Nodes"
    Set hbSegs = hbTip.HybridBodies.Add()
    hbSegs.Name = "Tip_Bulge_Boundaries"

    Dim nodeDict
    Set nodeDict = CreateObject("Scripting.Dictionary")

    Dim i, nid, x, y, z, p
    For i = 1 To UBound(nodeRows, 1)
        nid = SanitizeCatiaName(CStr(GetCsvValue(nodeRows, i, "node_id")))
        x = CsvDbl(GetCsvValue(nodeRows, i, "x_mm"))
        y = CsvDbl(GetCsvValue(nodeRows, i, "y_mm"))
        z = CsvDbl(GetCsvValue(nodeRows, i, "z_mm"))
        Set p = hsf.AddNewPointCoord(x, y, z)
        p.Name = nid
        hbNodes.AppendHybridShape p
        If nodeDict.Exists(nid) Then nodeDict.Remove nid
        nodeDict.Add nid, p
        TrySetFeatureColor p, 210, 150, 60
    Next

    If fso.FileExists(segPath) Then
        Dim segRows, sid, s1, s2, lineObj
        segRows = ReadCsvRows(segPath)
        For i = 1 To UBound(segRows, 1)
            sid = SanitizeCatiaName(CStr(GetCsvValue(segRows, i, "segment_id")))
            s1 = SanitizeCatiaName(CStr(GetCsvValue(segRows, i, "start_node")))
            s2 = SanitizeCatiaName(CStr(GetCsvValue(segRows, i, "end_node")))
            If nodeDict.Exists(s1) And nodeDict.Exists(s2) Then
                Set lineObj = hsf.AddNewLinePtPt(part.CreateReferenceFromObject(nodeDict.Item(s1)), part.CreateReferenceFromObject(nodeDict.Item(s2)))
                lineObj.Name = sid
                hbSegs.AppendHybridShape lineObj
                TrySetFeatureColor lineObj, 210, 150, 60
            Else
                AppendWarning "Tip-side bulge boundary skipped due to missing node: " & sid & " (" & s1 & " -> " & s2 & ")"
            End If
        Next
    End If

    If fso.FileExists(secPath) Then
        GenerateTipBulgeLoftSectionsFromCsv part, hsf, hbTip, nodeDict, secPath
    ElseIf fso.FileExists(surfPath) Then
        GenerateGenericSurfacesFromCsv part, hsf, hbTip, nodeDict, surfPath, "Tip_Bulge_Surfaces", "Tip_Bulge_Surface_Boundaries"
    End If

    If ParamBool(params, "tip_bulge_hide_original_rib_fills", False) Then
        On Error Resume Next
        If Not (ribFills(1) Is Nothing) Then HideFeatureSafely ribFills(1)
        If Not (ribFills(nRibs) Is Nothing) Then HideFeatureSafely ribFills(nRibs)
        Err.Clear
        On Error GoTo 0
    End If
End Sub


Sub GenerateTipBulgeLoftSectionsFromCsv(part, hsf, hbTip, nodeDict, secPath)
    ' Fast v20 method: create one loft per side through section splines.
    ' This avoids hundreds of individual Fill panels and prevents CATIA from appearing
    ' to hang when the tip-side bulge grid is dense.
    Dim rows
    rows = ReadCsvRows(secPath)
    If UBound(rows, 1) < 1 Then Exit Sub

    Dim hbSections, hbLofts
    Set hbSections = hbTip.HybridBodies.Add()
    hbSections.Name = "Tip_Bulge_Section_Curves"
    Set hbLofts = hbTip.HybridBodies.Add()
    hbLofts.Name = "Tip_Bulge_Lofts"

    Dim sideName
    For Each sideName In Array("L", "R")
        GenerateTipBulgeLoftForSide part, hsf, hbSections, hbLofts, nodeDict, rows, CStr(sideName)
    Next
End Sub

Sub GenerateTipBulgeLoftForSide(part, hsf, hbSections, hbLofts, nodeDict, rows, sideName)
    Dim maxOrder, r, xo
    maxOrder = 0
    For r = 1 To UBound(rows, 1)
        If UCase(CStr(GetCsvValue(rows, r, "side"))) = UCase(sideName) Then
            xo = CLng(CsvDbl(GetCsvValueDefault(rows, r, "x_order", "0")))
            If xo > maxOrder Then maxOrder = xo
        End If
    Next
    If maxOrder < 2 Then
        AppendWarning "Tip-side bulge loft skipped for side " & sideName & ": not enough sections."
        Exit Sub
    End If

    Dim sectionCurves()
    ReDim sectionCurves(maxOrder)
    Dim i, spline
    For i = 1 To maxOrder
        Set sectionCurves(i) = Nothing
    Next
    For i = 1 To maxOrder
        Set spline = MakeTipBulgeSectionSpline(part, hsf, hbSections, nodeDict, rows, sideName, i)
        If Not (spline Is Nothing) Then
            Set sectionCurves(i) = spline
        End If
    Next

    On Error Resume Next
    Err.Clear
    Dim loft
    Set loft = hsf.AddNewLoft()
    If Err.Number <> 0 Then
        AppendWarning "Could not create tip-side bulge loft object for side " & sideName & ": " & Err.Description
        Err.Clear
        On Error GoTo 0
        Exit Sub
    End If
    loft.Relimitation = 1
    loft.SectionCoupling = 1
    loft.CanonicalDetection = 2
    Dim added
    added = 0
    For i = 1 To maxOrder
        If Not (sectionCurves(i) Is Nothing) Then
            loft.AddSectionToLoft part.CreateReferenceFromObject(sectionCurves(i)), 1, Nothing
            added = added + 1
        End If
    Next
    If added < 2 Then
        AppendWarning "Tip-side bulge loft skipped for side " & sideName & ": less than two valid sections."
    Else
        loft.Name = "TIPBULGE_" & sideName & "_LOFT"
        hbLofts.AppendHybridShape loft
        TrySetFeatureColor loft, 210, 150, 60
    End If
    If Err.Number <> 0 Then
        AppendWarning "Tip-side bulge loft creation may fail for side " & sideName & ". CATIA error: " & Err.Description
        Err.Clear
    End If
    On Error GoTo 0
End Sub

Function MakeTipBulgeSectionSpline(part, hsf, hbSections, nodeDict, rows, sideName, xOrder)
    On Error Resume Next
    Err.Clear
    Dim spline
    Set spline = hsf.AddNewSpline()
    spline.SetSplineType 0
    spline.SetClosing 0
    Dim maxPoint, r, po
    maxPoint = 0
    For r = 1 To UBound(rows, 1)
        If UCase(CStr(GetCsvValue(rows, r, "side"))) = UCase(sideName) Then
            If CLng(CsvDbl(GetCsvValueDefault(rows, r, "x_order", "0"))) = CLng(xOrder) Then
                po = CLng(CsvDbl(GetCsvValueDefault(rows, r, "point_order", "0")))
                If po > maxPoint Then maxPoint = po
            End If
        End If
    Next
    If maxPoint < 2 Then
        Set MakeTipBulgeSectionSpline = Nothing
        On Error GoTo 0
        Exit Function
    End If

    Dim k, nid, added
    added = 0
    For k = 1 To maxPoint
        For r = 1 To UBound(rows, 1)
            If UCase(CStr(GetCsvValue(rows, r, "side"))) = UCase(sideName) Then
                If CLng(CsvDbl(GetCsvValueDefault(rows, r, "x_order", "0"))) = CLng(xOrder) Then
                    If CLng(CsvDbl(GetCsvValueDefault(rows, r, "point_order", "0"))) = CLng(k) Then
                        nid = SanitizeCatiaName(CStr(GetCsvValue(rows, r, "node_id")))
                        If nodeDict.Exists(nid) Then
                            spline.AddPoint part.CreateReferenceFromObject(nodeDict.Item(nid))
                            added = added + 1
                        Else
                            AppendWarning "Missing tip bulge section node: " & nid
                        End If
                    End If
                End If
            End If
        Next
    Next
    If added < 2 Or Err.Number <> 0 Then
        AppendWarning "Tip-side bulge section spline skipped: side=" & sideName & ", x_order=" & CStr(xOrder) & ". CATIA error: " & Err.Description
        Err.Clear
        Set MakeTipBulgeSectionSpline = Nothing
    Else
        spline.Name = "TIPBULGE_" & sideName & "_SEC_" & Right("000" & CStr(xOrder), 3)
        hbSections.AppendHybridShape spline
        TrySetFeatureColor spline, 210, 150, 60
        Set MakeTipBulgeSectionSpline = spline
    End If
    On Error GoTo 0
End Function

Sub GenerateGenericSurfacesFromCsv(part, hsf, hbParent, nodeDict, surfPath, surfSetName, auxSetName)
    Dim rows
    rows = ReadCsvRows(surfPath)
    If UBound(rows, 1) < 1 Then Exit Sub

    Dim hbSurf, hbAux
    Set hbSurf = hbParent.HybridBodies.Add()
    hbSurf.Name = surfSetName
    Set hbAux = hbParent.HybridBodies.Add()
    hbAux.Name = auxSetName

    Dim surfDict, bankDict
    Set surfDict = CreateObject("Scripting.Dictionary")
    Set bankDict = CreateObject("Scripting.Dictionary")

    Dim i, sid2, nid2, ord2, bnk
    For i = 1 To UBound(rows, 1)
        sid2 = SanitizeCatiaName(CStr(GetCsvValue(rows, i, "surface_id")))
        nid2 = SanitizeCatiaName(CStr(GetCsvValue(rows, i, "node_id")))
        ord2 = CLng(CsvDbl(GetCsvValueDefault(rows, i, "point_order", "1")))
        bnk = UCase(CStr(GetCsvValueDefault(rows, i, "bank", "")))
        If Len(sid2) > 0 And Len(nid2) > 0 Then
            If Not surfDict.Exists(sid2) Then
                surfDict.Add sid2, CreateObject("Scripting.Dictionary")
                bankDict.Add sid2, bnk
            End If
            If surfDict.Item(sid2).Exists(CStr(ord2)) Then surfDict.Item(sid2).Remove CStr(ord2)
            surfDict.Item(sid2).Add CStr(ord2), nid2
        End If
    Next

    Dim sidKey, pointDict, nPts, j, p1id, p2id, edgeObj, fillObj
    For Each sidKey In surfDict.Keys
        Set pointDict = surfDict.Item(sidKey)
        nPts = pointDict.Count
        If nPts >= 3 Then
            On Error Resume Next
            Err.Clear
            Set fillObj = hsf.AddNewFill()
            If Err.Number <> 0 Then
                AppendWarning "Could not create surface Fill: " & CStr(sidKey) & ". CATIA error: " & Err.Description
                Err.Clear
            Else
                For j = 1 To nPts
                    p1id = pointDict.Item(CStr(j))
                    If j = nPts Then
                        p2id = pointDict.Item(CStr(1))
                    Else
                        p2id = pointDict.Item(CStr(j + 1))
                    End If
                    If nodeDict.Exists(p1id) And nodeDict.Exists(p2id) Then
                        Set edgeObj = hsf.AddNewLinePtPt(part.CreateReferenceFromObject(nodeDict.Item(p1id)), part.CreateReferenceFromObject(nodeDict.Item(p2id)))
                        edgeObj.Name = CStr(sidKey) & "_edge_" & CStr(j)
                        hbAux.AppendHybridShape edgeObj
                        fillObj.AddBound part.CreateReferenceFromObject(edgeObj)
                    Else
                        AppendWarning "Surface skipped missing node in " & CStr(sidKey) & ": " & p1id & " or " & p2id
                    End If
                Next
                fillObj.Continuity = 0
                fillObj.Detection = 2
                fillObj.Name = CStr(sidKey)
                hbSurf.AppendHybridShape fillObj
                ApplySuspensionBankColor fillObj, CStr(bankDict.Item(sidKey))
                If Err.Number <> 0 Then
                    AppendWarning "Surface update may fail for " & CStr(sidKey) & ". CATIA error: " & Err.Description
                    Err.Clear
                End If
            End If
            On Error GoTo 0
        End If
    Next
End Sub


' =============================================================================
' Optional finite fabric-thickness offsets for CFD/FEM CAD preparation
' =============================================================================
Sub ApplyFabricThicknessOffsets(part, hsf)
    If gFabricThicknessMm <= 0.0 Then Exit Sub
    If gFabricThicknessMode = "none" Then Exit Sub

    Dim hbThick
    Set hbThick = part.HybridBodies.Add()
    hbThick.Name = "05_Fabric_Thickness_Offsets"

    Dim hb
    On Error Resume Next
    Err.Clear
    Set hb = part.HybridBodies.Item("02_Canopy_Surfaces")
    If Err.Number = 0 Then ApplyOffsetsRecursive part, hsf, hb, hbThick, "canopy"
    Err.Clear
    If gFabricThicknessIncludeStabilizers Then
        Set hb = part.HybridBodies.Item("03B_Canopy_Stabilizers")
        If Err.Number = 0 Then ApplyOffsetsRecursive part, hsf, hb, hbThick, "stabilizer"
        Err.Clear
    End If
    If gFabricThicknessIncludeTipBulge Then
        Set hb = part.HybridBodies.Item("03C_Tip_Side_Bulge")
        If Err.Number = 0 Then ApplyOffsetsRecursive part, hsf, hb, hbThick, "tip_bulge"
        Err.Clear
    End If
    On Error GoTo 0
End Sub

Sub ApplyOffsetsRecursive(part, hsf, hbSource, hbDest, groupName)
    Dim i, feat
    On Error Resume Next
    For i = 1 To hbSource.HybridShapes.Count
        Set feat = hbSource.HybridShapes.Item(i)
        If Err.Number = 0 Then
            If IsLikelySurfaceFeature(feat.Name) Then
                If (Not gFabricThicknessIncludeRibs) And StartsWithText(feat.Name, "Rib_Fill") Then
                    ' User requested to skip ribs.
                Else
                    MakeFabricOffsetForFeature part, hsf, hbDest, feat, groupName
                End If
            End If
        End If
        Err.Clear
    Next
    Dim child
    For i = 1 To hbSource.HybridBodies.Count
        Set child = hbSource.HybridBodies.Item(i)
        If Err.Number = 0 Then ApplyOffsetsRecursive part, hsf, child, hbDest, groupName
        Err.Clear
    Next
    On Error GoTo 0
End Sub

Function StartsWithText(s, prefix)
    StartsWithText = (Left(CStr(s), Len(CStr(prefix))) = CStr(prefix))
End Function

Function IsLikelySurfaceFeature(nameText)
    Dim n
    n = CStr(nameText)
    IsLikelySurfaceFeature = False
    If InStr(1, n, "Surface", vbTextCompare) > 0 Then IsLikelySurfaceFeature = True
    If StartsWithText(n, "Rib_Fill") Then IsLikelySurfaceFeature = True
    If InStr(1, n, "Loft", vbTextCompare) > 0 Then IsLikelySurfaceFeature = True
    If InStr(1, n, "PANEL", vbTextCompare) > 0 Then IsLikelySurfaceFeature = True
    If InStr(1, n, "STAB_", vbTextCompare) > 0 Then IsLikelySurfaceFeature = True
End Function

Sub MakeFabricOffsetForFeature(part, hsf, hbDest, feat, groupName)
    On Error Resume Next
    Err.Clear
    Dim refFeat, off1, off2, halfT, orientSingle
    Set refFeat = part.CreateReferenceFromObject(feat)
    halfT = gFabricThicknessMm / 2.0
    If gFabricThicknessMode = "single_offset" Then
        orientSingle = False
        If gFabricThicknessOffsetSide = "opposite" Then orientSingle = True
        Set off1 = hsf.AddNewOffset(refFeat, gFabricThicknessMm, orientSingle, 0.01)
        off1.Name = "THICK_" & groupName & "_" & feat.Name
        hbDest.AppendHybridShape off1
    Else
        Set off1 = hsf.AddNewOffset(refFeat, halfT, False, 0.01)
        off1.Name = "THICK_PLUS_" & groupName & "_" & feat.Name
        hbDest.AppendHybridShape off1
        Err.Clear
        Set off2 = hsf.AddNewOffset(refFeat, halfT, True, 0.01)
        off2.Name = "THICK_MINUS_" & groupName & "_" & feat.Name
        hbDest.AppendHybridShape off2
    End If
    If Err.Number <> 0 Then
        AppendWarning "Fabric-thickness offset rejected for " & feat.Name & ". CATIA error: " & Err.Description
        Err.Clear
    End If
    On Error GoTo 0
End Sub

' =============================================================================
' Optional suspension-line network generation
' =============================================================================
Sub GenerateSuspensionLinesFromCsv(part, hsf, baseFolder, params)
    Dim nodesFile, segmentsFile, nodesPath, segmentsPath
    nodesFile = CStr(GetParam(params, "suspension_nodes_file", "ramair_suspension_nodes.csv"))
    segmentsFile = CStr(GetParam(params, "suspension_segments_file", "ramair_suspension_segments.csv"))
    nodesPath = ResolveInputPath(baseFolder, nodesFile)
    segmentsPath = ResolveInputPath(baseFolder, segmentsFile)

    If Not fso.FileExists(nodesPath) Then
        AppendWarning "enable_suspension_lines=1, but missing file: " & nodesPath
        Exit Sub
    End If
    If Not fso.FileExists(segmentsPath) Then
        AppendWarning "enable_suspension_lines=1, but missing file: " & segmentsPath
        Exit Sub
    End If

    Dim nodeRows, segRows
    nodeRows = ReadCsvRows(nodesPath)
    segRows = ReadCsvRows(segmentsPath)

    If UBound(nodeRows, 1) < 1 Then
        AppendWarning "Suspension nodes CSV is empty."
        Exit Sub
    End If
    If UBound(segRows, 1) < 1 Then
        AppendWarning "Suspension segments CSV is empty."
        Exit Sub
    End If

    Dim hbSusp, hbNodes, hbSegs
    Set hbSusp = part.HybridBodies.Add()
    hbSusp.Name = "04_Suspension_Lines"
    Set hbNodes = hbSusp.HybridBodies.Add()
    hbNodes.Name = "Suspension_Nodes"
    Set hbSegs = hbSusp.HybridBodies.Add()
    hbSegs.Name = "Suspension_Segments"

    Dim nodeDict, coordDict
    Set nodeDict = CreateObject("Scripting.Dictionary")
    Set coordDict = CreateObject("Scripting.Dictionary")

    Dim i, nid, x, y, z, p, nType, bank
    For i = 1 To UBound(nodeRows, 1)
        nid = SanitizeCatiaName(CStr(GetCsvValue(nodeRows, i, "node_id")))
        x = CsvDbl(GetCsvValue(nodeRows, i, "x_mm"))
        y = CsvDbl(GetCsvValue(nodeRows, i, "y_mm"))
        z = CsvDbl(GetCsvValue(nodeRows, i, "z_mm"))
        nType = LCase(CStr(GetCsvValueDefault(nodeRows, i, "node_type", "node")))
        bank = UCase(CStr(GetCsvValueDefault(nodeRows, i, "bank", "")))

        Set p = hsf.AddNewPointCoord(x, y, z)
        p.Name = nid
        hbNodes.AppendHybridShape p
        If nodeDict.Exists(nid) Then nodeDict.Remove nid
        nodeDict.Add nid, p
        If coordDict.Exists(nid) Then coordDict.Remove nid
        coordDict.Add nid, Array(x, y, z)
        If nType = "anchor" Then
            TrySetFeatureColor p, 255, 255, 255
        ElseIf nType = "cascade" Then
            TrySetFeatureColor p, 0, 255, 255
        ElseIf nType = "riser" Or nType = "brake_actuator" Then
            TrySetFeatureColor p, 255, 0, 255
        ElseIf bank = "SLIDER" Then
            TrySetFeatureColor p, 160, 160, 160
        End If
    Next

    Dim hbTubes
    If gEnableSuspensionTubeGeometry Or LCase(CStr(GetParam(params, "line_visualization_mode", "curve"))) = "tube" Or LCase(CStr(GetParam(params, "line_visualization_mode", "curve"))) = "cylinder_surface" Then
        Set hbTubes = hbSusp.HybridBodies.Add()
        hbTubes.Name = "Suspension_Line_Tube_Surfaces"
        gEnableSuspensionTubeGeometry = True
    End If

    Dim sid, s1, s2, lineObj
    For i = 1 To UBound(segRows, 1)
        sid = SanitizeCatiaName(CStr(GetCsvValue(segRows, i, "segment_id")))
        s1 = SanitizeCatiaName(CStr(GetCsvValue(segRows, i, "start_node")))
        s2 = SanitizeCatiaName(CStr(GetCsvValue(segRows, i, "end_node")))
        bank = UCase(CStr(GetCsvValueDefault(segRows, i, "bank", "")))
        If nodeDict.Exists(s1) And nodeDict.Exists(s2) Then
            Dim pStart, pEnd
            Set pStart = nodeDict.Item(s1)
            Set pEnd = nodeDict.Item(s2)
            Set lineObj = hsf.AddNewLinePtPt(part.CreateReferenceFromObject(pStart), part.CreateReferenceFromObject(pEnd))
            lineObj.Name = sid & "_" & bank
            hbSegs.AppendHybridShape lineObj
            ApplySuspensionBankColor lineObj, bank
            If gEnableSuspensionTubeGeometry Then
                Dim dia, matLineType
                dia = CsvDbl(GetCsvValueDefault(segRows, i, "diameter_mm", CStr(gDefaultSuspensionLineDiameterMm)))
                If dia <= 0.0 Then dia = gDefaultSuspensionLineDiameterMm
                matLineType = LCase(CStr(GetCsvValueDefault(segRows, i, "line_type", "structural")))
                If matLineType <> "slider" And matLineType <> "payload" And matLineType <> "agu" And matLineType <> "stabilizer" And matLineType <> "tip_bulge" Then
                    TryMakeLineCylinder part, hsf, hbTubes, sid & "_tube", coordDict.Item(s1), coordDict.Item(s2), dia / 2.0, bank
                End If
            End If
        Else
            AppendWarning "Suspension segment skipped because one node was missing: " & sid & " (" & s1 & " -> " & s2 & ")"
        End If
    Next

    GenerateSuspensionSurfacesFromCsv part, hsf, baseFolder, params, hbSusp, nodeDict

    If gEnableSuspensionTubeGeometry Then
        AppendWarning "Experimental CATIA tube/cylinder mode was requested. Robust CFD/FEM workflow is centerline curves + Suspension_Lines\ramair_suspension_segment_analysis.csv; create cylinders later in the mesher if needed."
    End If
End Sub


Sub TryMakeLineCylinder(part, hsf, hbTubes, objName, p1arr, p2arr, radiusMm, bank)
    On Error Resume Next
    Err.Clear
    Dim x1, y1, z1, x2, y2, z2, dx, dy, dz, L
    x1 = CDbl(p1arr(0)) : y1 = CDbl(p1arr(1)) : z1 = CDbl(p1arr(2))
    x2 = CDbl(p2arr(0)) : y2 = CDbl(p2arr(1)) : z2 = CDbl(p2arr(2))
    dx = x2 - x1 : dy = y2 - y1 : dz = z2 - z1
    L = Sqr(dx*dx + dy*dy + dz*dz)
    If L <= 0.001 Or radiusMm <= 0.0 Then Exit Sub
    Dim pCenter, dir, cyl
    Set pCenter = hsf.AddNewPointCoord(x1, y1, z1)
    pCenter.Name = objName & "_start"
    hbTubes.AppendHybridShape pCenter
    Set dir = hsf.AddNewDirectionByCoord(dx / L, dy / L, dz / L)
    Set cyl = hsf.AddNewCylinder(part.CreateReferenceFromObject(pCenter), radiusMm, L, 0.0, dir)
    cyl.Name = objName
    hbTubes.AppendHybridShape cyl
    ApplySuspensionBankColor cyl, bank
    If Err.Number <> 0 Then
        AppendWarning "Suspension tube/cylinder rejected for " & objName & ". CATIA error: " & Err.Description
        Err.Clear
    End If
    On Error GoTo 0
End Sub

Sub GenerateSuspensionSurfacesFromCsv(part, hsf, baseFolder, params, hbSusp, nodeDict)
    Dim surfFile, surfPath
    surfFile = CStr(GetParam(params, "suspension_surfaces_file", "ramair_suspension_surfaces.csv"))
    surfPath = ResolveInputPath(baseFolder, surfFile)
    If Not fso.FileExists(surfPath) Then Exit Sub

    Dim rows
    rows = ReadCsvRows(surfPath)
    If UBound(rows, 1) < 1 Then Exit Sub

    Dim hbSurf, hbAux
    Set hbSurf = hbSusp.HybridBodies.Add()
    hbSurf.Name = "Suspension_Surfaces"
    Set hbAux = hbSusp.HybridBodies.Add()
    hbAux.Name = "Suspension_Surface_Boundaries"

    Dim surfDict, bankDict
    Set surfDict = CreateObject("Scripting.Dictionary")
    Set bankDict = CreateObject("Scripting.Dictionary")

    Dim i, sid2, nid2, ord2, bnk
    For i = 1 To UBound(rows, 1)
        sid2 = SanitizeCatiaName(CStr(GetCsvValue(rows, i, "surface_id")))
        nid2 = SanitizeCatiaName(CStr(GetCsvValue(rows, i, "node_id")))
        ord2 = CLng(CsvDbl(GetCsvValueDefault(rows, i, "point_order", "1")))
        bnk = UCase(CStr(GetCsvValueDefault(rows, i, "bank", "")))
        If Len(sid2) > 0 And Len(nid2) > 0 Then
            If Not surfDict.Exists(sid2) Then
                surfDict.Add sid2, CreateObject("Scripting.Dictionary")
                bankDict.Add sid2, bnk
            End If
            surfDict.Item(sid2).Add CStr(ord2), nid2
        End If
    Next

    Dim sidKey, pointDict, nPts, j, p1id, p2id, edgeObj, fillObj
    For Each sidKey In surfDict.Keys
        Set pointDict = surfDict.Item(sidKey)
        nPts = pointDict.Count
        If nPts >= 3 Then
            On Error Resume Next
            Err.Clear
            Set fillObj = hsf.AddNewFill()
            If Err.Number <> 0 Then
                AppendWarning "Could not create suspension surface Fill: " & CStr(sidKey) & ". CATIA error: " & Err.Description
                Err.Clear
            Else
                For j = 1 To nPts
                    p1id = pointDict.Item(CStr(j))
                    If j = nPts Then
                        p2id = pointDict.Item(CStr(1))
                    Else
                        p2id = pointDict.Item(CStr(j + 1))
                    End If
                    If nodeDict.Exists(p1id) And nodeDict.Exists(p2id) Then
                        Set edgeObj = hsf.AddNewLinePtPt(part.CreateReferenceFromObject(nodeDict.Item(p1id)), part.CreateReferenceFromObject(nodeDict.Item(p2id)))
                        edgeObj.Name = CStr(sidKey) & "_edge_" & CStr(j)
                        hbAux.AppendHybridShape edgeObj
                        fillObj.AddBound part.CreateReferenceFromObject(edgeObj)
                    Else
                        AppendWarning "Suspension surface skipped missing node in " & CStr(sidKey) & ": " & p1id & " or " & p2id
                    End If
                Next
                fillObj.Continuity = 0
                fillObj.Detection = 2
                fillObj.Name = CStr(sidKey)
                hbSurf.AppendHybridShape fillObj
                ApplySuspensionBankColor fillObj, CStr(bankDict.Item(sidKey))
                If Err.Number <> 0 Then
                    AppendWarning "Suspension surface update may fail for " & CStr(sidKey) & ". CATIA error: " & Err.Description
                    Err.Clear
                End If
            End If
            On Error GoTo 0
        End If
    Next
End Sub

Function SanitizeCatiaName(s)
    Dim out
    out = Trim(CStr(s))
    out = Replace(out, " ", "_")
    out = Replace(out, "/", "_")
    out = Replace(out, "\\", "_")
    out = Replace(out, ":", "_")
    out = Replace(out, ";", "_")
    out = Replace(out, ",", "_")
    out = Replace(out, "(", "_")
    out = Replace(out, ")", "_")
    If Len(out) = 0 Then out = "unnamed"
    SanitizeCatiaName = out
End Function

Sub ApplySuspensionBankColor(featureObj, bank)
    If bank = "A" Then
        TrySetFeatureColor featureObj, 255, 0, 0
    ElseIf bank = "B" Then
        TrySetFeatureColor featureObj, 255, 140, 0
    ElseIf bank = "C" Then
        TrySetFeatureColor featureObj, 0, 120, 255
    ElseIf bank = "D" Then
        TrySetFeatureColor featureObj, 0, 170, 0
    ElseIf bank = "BRK" Then
        TrySetFeatureColor featureObj, 180, 0, 220
    ElseIf bank = "SLIDER" Then
        TrySetFeatureColor featureObj, 120, 120, 120
    ElseIf bank = "STAB" Then
        TrySetFeatureColor featureObj, 180, 110, 40
    ElseIf bank = "TIPBULGE" Then
        TrySetFeatureColor featureObj, 210, 150, 60
    ElseIf bank = "PAYLOAD" Then
        TrySetFeatureColor featureObj, 60, 60, 60
    ElseIf bank = "AGU" Then
        TrySetFeatureColor featureObj, 100, 100, 160
    ElseIf bank = "LOWER" Then
        TrySetFeatureColor featureObj, 40, 40, 40
    Else
        TrySetFeatureColor featureObj, 255, 255, 255
    End If
End Sub

Sub TrySetFeatureColor(featureObj, r, g, b)
    On Error Resume Next
    Dim sel
    Set sel = CATIA.ActiveDocument.Selection
    sel.Clear
    sel.Add featureObj
    sel.VisProperties.SetRealColor CLng(r), CLng(g), CLng(b), 1
    sel.Clear
    On Error GoTo 0
End Sub
